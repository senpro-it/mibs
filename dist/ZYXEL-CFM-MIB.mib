-- ZyXEL Communications Corporation
-- Private Enterprise MIB definition 
  
-- This file describes the ZyXEL Communications Corporation Enterprise MIB.
-- It contains ZyXEL products OIDs, and common managed objects.

-- ZYXEL-CFM-MIB.mib
-- Revision 1.9  2013/12/06 

ZYXEL-CFM-MIB DEFINITIONS ::= BEGIN

    IMPORTS
	OBJECT-TYPE
		FROM SNMPv2-SMI			-- RFC2578	
		
	MODULE-IDENTITY
		FROM SNMPv2-SMI
	
	TDomain
		FROM SNMPv2-TC			-- RFC2579

	EnabledStatus
		FROM  P-BRIDGE-MIB
 
  dot1agCfmMdIndex 
		FROM IEEE8021-CFM-MIB
	
	dot1agCfmMaIndex
		FROM IEEE8021-CFM-MIB	
	
	dot1agCfmMepIdentifier
		FROM IEEE8021-CFM-MIB   	
  
  IpAddress
      FROM SNMPv2-SMI
  
  Unsigned32
  		FROM SNMPv2-SMI

	esMgmt			
		FROM ZYXEL-ES-SMI;

	zyxelCfm MODULE-IDENTITY
		LAST-UPDATED	"201207010000Z"    
		ORGANIZATION "Enterprise Solution ZyXEL"     
		CONTACT-INFO
			""	   
		DESCRIPTION
			"The subtree for cfm"
		::= { esMgmt 13 }	
	
	zyxelCfmSetup			OBJECT IDENTIFIER ::= { zyxelCfm 1 }
	zyxelCfmStatus			OBJECT IDENTIFIER ::= { zyxelCfm 2 }	

--  1.zyxelCfmSetup 
	
		  
		    	    
		zyCfmState OBJECT-TYPE
	    SYNTAX      EnabledStatus
	    MAX-ACCESS  	read-write
	    STATUS      current
	    DESCRIPTION
	       "Enabled/disabled CFM on the switch."
	    ::= { zyxelCfmSetup 1 }  

		zyxelCfmMibObjects         OBJECT IDENTIFIER ::= { zyxelCfmSetup 2 }
	
-- ******************************************************************
-- Groups in the CFM MIB Module
-- ******************************************************************
	
-- ******************************************************************
-- The MEP Table
-- ****************************************************************** 
	    zyCfmMgmtIpAddressDomain OBJECT-TYPE
        SYNTAX  TDomain
        MAX-ACCESS  read-write
        STATUS  current
        DESCRIPTION
        "This object indicates the transport type of the address contained in sender ID TLV. 
		 Typical values will be one of (not all inclusive) list:
			transportDomainUdpIpv4  (1.3.6.1.2.1.100.1.1)
			snmpIeee802Domain        (1.3.6.1.6.1.6)"
        ::= { zyxelCfmMibObjects 1 }
 
 	zyCfmMgmtIpAddress OBJECT-TYPE
        SYNTAX  IpAddress
        MAX-ACCESS  read-write
        STATUS  current
        DESCRIPTION
        "The address that can be used to manage the responding MP."
        ::= { zyxelCfmMibObjects 2 }
		
		zyxelCfmMepTable OBJECT-TYPE
	    SYNTAX      SEQUENCE OF ZyxelCfmMepEntry
	    MAX-ACCESS  not-accessible
	    STATUS      current
	    DESCRIPTION
	    "The table contains CFM MEP configuration."
	    ::= { zyxelCfmMibObjects 3 }        
	    
	   	zyxelCfmMepEntry OBJECT-TYPE
	    SYNTAX      ZyxelCfmMepEntry
	    MAX-ACCESS  not-accessible
	    STATUS      current
	    DESCRIPTION
	    "An entry contains CFM MEP configuration. "
	    INDEX { dot1agCfmMdIndex,
	            dot1agCfmMaIndex,
	            dot1agCfmMepIdentifier
	          }
	    ::= { zyxelCfmMepTable 1 }
    
		ZyxelCfmMepEntry ::= SEQUENCE {
	      zyCfmMepTransmitLbmDataTlvSize           Unsigned32	      
	    }
       	    
		zyCfmMepTransmitLbmDataTlvSize OBJECT-TYPE
	    SYNTAX      Unsigned32 (0..1500)
	    MAX-ACCESS  	read-write
	    STATUS      current
	    DESCRIPTION
	    "Size of data to be included in the LBM data TLV."
	    REFERENCE
	       ""
	    ::= { zyxelCfmMepEntry 1 }  

		
--  2.zyxelCfmStatus
		zyCfmLinkTraceClear OBJECT-TYPE
	    SYNTAX      EnabledStatus
	    MAX-ACCESS 	read-write
	    STATUS      current
	    DESCRIPTION
	       "Clears the link trace database."
	    ::= { zyxelCfmStatus 1 }  
		
		zyCfmMepCcmDbClear OBJECT-TYPE
	    SYNTAX      EnabledStatus
	    MAX-ACCESS 	read-write
	    STATUS      current
	    DESCRIPTION
	       "Clears the MEP CCM database."
	    ::= { zyxelCfmStatus 2 }  
		
		zyCfmMepDefectsClear OBJECT-TYPE
	    SYNTAX      EnabledStatus
	    MAX-ACCESS 	read-write
	    STATUS      current
	    DESCRIPTION
	       "Clears the MEP-defects database."
	    ::= { zyxelCfmStatus 3 }  
		
		zyCfmMipCcmDbClear OBJECT-TYPE
	    SYNTAX      EnabledStatus
	    MAX-ACCESS 	read-write
	    STATUS      current
	    DESCRIPTION
	       "Clears the MIP CCM database."
	    ::= { zyxelCfmStatus 4 }  
END
