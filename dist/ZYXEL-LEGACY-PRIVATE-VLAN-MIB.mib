-- ZyXEL Communications Corporation
-- Private Enterprise MIB definition 
  
-- This file describes the ZyXEL Communications Corporation Enterprise MIB.
-- It contains ZyXEL products OIDs, and common managed objects.

-- ZYXEL-LEGACY-PRIVATE-VLAN-MIB.mib
-- Revision 1.4  2013/12/06 

ZYXEL-LEGACY-PRIVATE-VLAN-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC

	PortList
		FROM  Q-BRIDGE-MIB

	esMgmt			
		FROM ZYXEL-ES-SMI;

	zyxelLegacyPrivateVlan MODULE-IDENTITY
		LAST-UPDATED	"201207010000Z"    
		ORGANIZATION "Enterprise Solution ZyXEL"     
		CONTACT-INFO
			""	   
		DESCRIPTION
			"The subtree for legacy private VLAN"
		::= { esMgmt 41 }	
		
	zyxelLegacyPrivateVlanSetup	 	OBJECT IDENTIFIER ::= { zyxelLegacyPrivateVlan 1 }                    
   
    
    zyLegacyPrivateVlanMaxNumberOfVlans OBJECT-TYPE
        SYNTAX      INTEGER
        MAX-ACCESS  read-only
        STATUS      current
        DESCRIPTION
         	"The maximum number of legacy private VLAN that can be created."
    	::= { zyxelLegacyPrivateVlanSetup 1 }
     
	zyxelLegacyPrivateVlanTable OBJECT-TYPE
		SYNTAX      SEQUENCE OF ZyxelLegacyPrivateVlanEntry
        MAX-ACCESS  not-accessible
		STATUS      current
		DESCRIPTION
			"The table contains legacy private VLAN configuration."       
        ::= { zyxelLegacyPrivateVlanSetup 2 }

	zyxelLegacyPrivateVlanEntry OBJECT-TYPE
        SYNTAX      ZyxelLegacyPrivateVlanEntry
        MAX-ACCESS  not-accessible
        STATUS      current
        DESCRIPTION 
        	"An entry contains legacy private VLAN configuration."
        INDEX { zyLegacyPrivateVlanVid }
    	::= { zyxelLegacyPrivateVlanTable 1 }

	ZyxelLegacyPrivateVlanEntry ::=
        SEQUENCE { 
            zyLegacyPrivateVlanVid                INTEGER,
            zyLegacyPrivateVlanName               DisplayString,
            zyLegacyPrivateVlanPromiscuousPorts   PortList,
            zyLegacyPrivateVlanRowStatus          RowStatus
   	}

	zyLegacyPrivateVlanVid OBJECT-TYPE
        SYNTAX      INTEGER (1..4094)
        MAX-ACCESS  not-accessible
        STATUS      current
        DESCRIPTION
         	"Private VLAN ID from 1 to 4094. This is the VLAN to which this rule applies."
    	::= { zyxelLegacyPrivateVlanEntry 1 }

	zyLegacyPrivateVlanName OBJECT-TYPE
        SYNTAX      DisplayString
        MAX-ACCESS  read-write
        STATUS      current
        DESCRIPTION
         	"Private VLAN name for identification purpose."
    	::= { zyxelLegacyPrivateVlanEntry 2 }


	zyLegacyPrivateVlanPromiscuousPorts OBJECT-TYPE
        SYNTAX      PortList
        MAX-ACCESS  read-write
        STATUS      current
        DESCRIPTION
         	"Promiscuous ports of private VLAN can communicate with any ports within this private VLAN. 
         	The other ports of this VLAN, which are not defined as promiscuous ports, will be added to the 
         	isolation list."
    	::= { zyxelLegacyPrivateVlanEntry 3 }

	zyLegacyPrivateVlanRowStatus OBJECT-TYPE
        SYNTAX      RowStatus
        MAX-ACCESS  read-create
        STATUS      current
        DESCRIPTION
         	"This object allows entries to be created and deleted from the legacy private VLAN table."        
    	::= { zyxelLegacyPrivateVlanEntry 4 }    
END
