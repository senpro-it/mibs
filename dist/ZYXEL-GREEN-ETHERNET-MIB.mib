-- ZyXEL Communications Corporation
-- Private Enterprise MIB definition 
  
-- This file describes the ZyXEL Communications Corporation Enterprise MIB.
-- It contains ZyXEL products OIDs, and common managed objects.

-- ZYXEL-GREEN-ETHERNET-MIB.mib
-- Revision 1.3  2013/12/06 

ZYXEL-GREEN-ETHERNET-MIB DEFINITIONS ::= BEGIN

    IMPORTS
	OBJECT-TYPE
		FROM SNMPv2-SMI			-- RFC2578	
		
	MODULE-IDENTITY
		FROM SNMPv2-SMI
	
	EnabledStatus
		FROM  P-BRIDGE-MIB
		
	dot1dBasePort
		FROM BRIDGE-MIB

	esMgmt			
		FROM ZYXEL-ES-SMI;

	zyxelGreenEthernet MODULE-IDENTITY
		LAST-UPDATED	"201207010000Z"    
		ORGANIZATION "Enterprise Solution ZyXEL"     
		CONTACT-INFO
			""	   
		DESCRIPTION
			"The subtree for Green Ethernet"
		::= { esMgmt 93 }

	zyxelGreenEthernetSetup     OBJECT IDENTIFIER ::= { zyxelGreenEthernet 1 }    

--  zyxelGreenEthernetSetup

        zyGreenEthernetEeeState OBJECT-TYPE  
        SYNTAX  EnabledStatus
        MAX-ACCESS  read-write
        STATUS  current
        DESCRIPTION	
        "Enable/Disable EEE"
        ::= { zyxelGreenEthernetSetup 1 }
        
        zyGreenEthernetAutoPowerDownState OBJECT-TYPE
        SYNTAX  EnabledStatus
        MAX-ACCESS  read-write
        STATUS  current
        DESCRIPTION
        "Enable/Disable Auto Power Down"
        ::= { zyxelGreenEthernetSetup 2 }

        zyGreenEthernetShortReachState OBJECT-TYPE
        SYNTAX  EnabledStatus
        MAX-ACCESS  read-write
        STATUS  current
        DESCRIPTION
        "Enable/Disable Short Reach"
        ::= { zyxelGreenEthernetSetup 3 }
                  
        zyxelGreenEthernetPortTable OBJECT-TYPE
        SYNTAX	SEQUENCE OF ZyxelGreenEthernetPortEntry
        MAX-ACCESS  not-accessible
        STATUS  current
        DESCRIPTION
        ""
        ::= { zyxelGreenEthernetSetup 4 }
       
		zyxelGreenEthernetPortEntry OBJECT-TYPE
        SYNTAX	ZyxelGreenEthernetPortEntry
        MAX-ACCESS	not-accessible
        STATUS	current
        DESCRIPTION    	
        "An entry in zyxelGreenEthernetPortTable."
        INDEX          	{ dot1dBasePort }
        ::= { zyxelGreenEthernetPortTable 1 }

        ZyxelGreenEthernetPortEntry ::=
           SEQUENCE {
        	zyGreenEthernetEeePortState				EnabledStatus,
        	zyGreenEthernetAutoPowerDownPortState	EnabledStatus,
        	zyGreenEthernetShortReachPortState		EnabledStatus
           }

        zyGreenEthernetEeePortState OBJECT-TYPE
        SYNTAX  EnabledStatus
        MAX-ACCESS  read-write
        STATUS  current
        DESCRIPTION
        "Enable/Disable EEE by port"
        ::= { zyxelGreenEthernetPortEntry 1 }

		zyGreenEthernetAutoPowerDownPortState OBJECT-TYPE
        SYNTAX  EnabledStatus
        MAX-ACCESS  read-write
        STATUS  current
        DESCRIPTION
        "Enable/Disable Auto Power Down by port"
        ::= { zyxelGreenEthernetPortEntry 2 }          
        
        zyGreenEthernetShortReachPortState OBJECT-TYPE
        SYNTAX  EnabledStatus
        MAX-ACCESS  read-write
        STATUS  current
        DESCRIPTION
        "Enable/Disable Auto Power Down by port"
        ::= { zyxelGreenEthernetPortEntry 3 }

             
END
