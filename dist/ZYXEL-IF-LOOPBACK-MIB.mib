-- ZyXEL Communications Corporation
-- Private Enterprise MIB definition 
  
-- This file describes the ZyXEL Communications Corporation Enterprise MIB.
-- It contains ZyXEL products OIDs, and common managed objects.

-- ZYXEL-IF-LOOPBACK-MIB.mib
-- Revision 1.4  2013/12/06 

ZYXEL-IF-LOOPBACK-MIB DEFINITIONS ::= BEGIN


    IMPORTS
	OBJECT-TYPE
		FROM SNMPv2-SMI			-- RFC2578	
		
	MODULE-IDENTITY
		FROM SNMPv2-SMI
	
	RowStatus
		FROM SNMPv2-TC			-- RFC2579
  	
	IpAddress
		FROM SNMPv2-SMI

	esMgmt			
		FROM ZYXEL-ES-SMI;

	zyxelIfLoopback MODULE-IDENTITY
		LAST-UPDATED	"201207010000Z"    
		ORGANIZATION "Enterprise Solution ZyXEL"     
		CONTACT-INFO
			""	   
		DESCRIPTION
			"The subtree for loopback interface"
		::= { esMgmt 28 }
				
 	zyxelIfLoopbackSetup    OBJECT IDENTIFIER ::= { zyxelIfLoopback 1 }		

-- ******************************************************************
-- *
-- 28.LOOPBACK_INTERFACE mib
-- *
-- ****************************************************************** 
                      
	zyIfLoopbackMaxNumberOfIfs OBJECT-TYPE
        SYNTAX  	INTEGER
        MAX-ACCESS  read-only
        STATUS  	current
        DESCRIPTION
		"The maximum number of loopback interface that can be created."
	::= { zyxelIfLoopbackSetup 1 }

-- * 
-- * zyxelIfLoopbackTable  
-- *
	zyxelIfLoopbackTable OBJECT-TYPE
	 	SYNTAX      SEQUENCE OF ZyxelIfLoopbackEntry
	    MAX-ACCESS  not-accessible
	    STATUS      current
	    DESCRIPTION
		"The table contains loopback interface configuration."              
    ::= { zyxelIfLoopbackSetup 2 }  
    
    zyxelIfLoopbackEntry OBJECT-TYPE
        SYNTAX      ZyxelIfLoopbackEntry
        MAX-ACCESS  not-accessible
        STATUS      current
        DESCRIPTION
		"An entry contains loopback interface configuration."
        INDEX {           
            zyIfLoopbackId                 
        }
    ::= { zyxelIfLoopbackTable 1 }

    ZyxelIfLoopbackEntry ::=
        SEQUENCE {
		zyIfLoopbackId			INTEGER,
		zyIfLoopbackName		OCTET STRING,
		zyIfLoopbackIpAddress	IpAddress,
		zyIfLoopbackMask		IpAddress,
		zyIfLoopbackRowStatus	RowStatus
        }
    
    zyIfLoopbackId OBJECT-TYPE
        SYNTAX  	INTEGER
        MAX-ACCESS 	not-accessible
        STATUS      current
        DESCRIPTION
		"Display the identification number of the loopback interface."
    ::= { zyxelIfLoopbackEntry 1 }

    zyIfLoopbackName OBJECT-TYPE
        SYNTAX      OCTET STRING
        MAX-ACCESS  read-write
        STATUS      current
        DESCRIPTION
		"A descriptive name (up to 32 printable ASCII characters) for identification purposes."
    ::= { zyxelIfLoopbackEntry 2 }

    zyIfLoopbackIpAddress OBJECT-TYPE
        SYNTAX      IpAddress
        MAX-ACCESS  read-write
        STATUS      current
        DESCRIPTION
		"The IP address of an IP routing domain that is associated to a loopback interface."            
    ::= { zyxelIfLoopbackEntry 3 }      

    zyIfLoopbackMask OBJECT-TYPE
        SYNTAX      IpAddress
        MAX-ACCESS  read-write
        STATUS      current
        DESCRIPTION
		"The subnet mask of an IP routing domain that is associated to a loopback interface."            
    ::= { zyxelIfLoopbackEntry 4 }     	
                               
    zyIfLoopbackRowStatus OBJECT-TYPE
        SYNTAX      RowStatus
        MAX-ACCESS  read-create
        STATUS      current
        DESCRIPTION
		"This object allows entries to be created and deleted from the loopback interface table."            
    ::= { zyxelIfLoopbackEntry 5 }                    
    
    
  END
