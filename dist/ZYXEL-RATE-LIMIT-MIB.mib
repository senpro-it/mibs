-- ZyXEL Communications Corporation
-- Private Enterprise MIB definition 
  
-- This file describes the ZyXEL Communications Corporation Enterprise MIB.
-- It contains ZyXEL products OIDs, and common managed objects.

-- ZYXEL-RATE-LIMIT-MIB.mib
-- Revision 1.5  2013/12/06 

ZYXEL-RATE-LIMIT-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	dot1dBasePort
       	FROM BRIDGE-MIB

	esMgmt			
		FROM ZYXEL-ES-SMI;

	zyxelRateLimit MODULE-IDENTITY
		LAST-UPDATED	"201207010000Z"    
		ORGANIZATION "Enterprise Solution ZyXEL"     
		CONTACT-INFO
			""	   
		DESCRIPTION
			"The subtree for rate limit"
		::= { esMgmt 72 }
		
	zyxelRateLimitSetup     OBJECT IDENTIFIER ::= { zyxelRateLimit 1 }
	
-- *******************************************************************
-- *
-- * zyxelRateLimitSetup
-- *
-- *******************************************************************

-- zyxelRateLimitState
        zyRateLimitState OBJECT-TYPE
        SYNTAX  EnabledStatus
        MAX-ACCESS  read-write
        STATUS  current
        DESCRIPTION
			"Enabled/Disabled ingress/egress rate limiting for the switch."
        ::= { zyxelRateLimitSetup 1 }

-- zyxelRateLimitPortTable
        zyxelRateLimitPortTable OBJECT-TYPE
        SYNTAX	SEQUENCE OF ZyxelRateLimitPortEntry
        MAX-ACCESS  not-accessible
        STATUS  current
        DESCRIPTION
			"The table contains rate limit port configuration."
        ::= { zyxelRateLimitSetup 2 }
        
		zyxelRateLimitPortEntry OBJECT-TYPE
        SYNTAX	ZyxelRateLimitPortEntry
        MAX-ACCESS	not-accessible
        STATUS	current
        DESCRIPTION    	
			"An entry contains rate limit port configuration. "
        INDEX          	{ dot1dBasePort }
        ::= { zyxelRateLimitPortTable 1 }

        ZyxelRateLimitPortEntry ::=
           SEQUENCE {	
        	zyRateLimitPortCommitState 	EnabledStatus,
        	zyRateLimitPortCommitRate	INTEGER,
			zyRateLimitPortPeakState	EnabledStatus,
			zyRateLimitPortPeakRate		INTEGER,
			zyRateLimitPortEgressState	EnabledStatus,
			zyRateLimitPortEgressRate	INTEGER			
								
           }  
           
        zyRateLimitPortCommitState OBJECT-TYPE
        SYNTAX  EnabledStatus
        MAX-ACCESS  read-write
        STATUS  current
        DESCRIPTION
			"Enabled/Disabled ingress commit rate limiting  on the specified port."
        ::= { zyxelRateLimitPortEntry 1 }           
        
        zyRateLimitPortCommitRate OBJECT-TYPE
        SYNTAX  INTEGER
        MAX-ACCESS  read-write
        STATUS  current
        DESCRIPTION
			"Specify the guaranteed bandwidth allowed in kilobits per second (Kbps) for the incoming traffic flow 
			on the specified port. The commit rate should be less than the peak rate. The sum of commit rates 
			cannot be greater than or equal to the uplink bandwidth."
        ::= { zyxelRateLimitPortEntry 2 } 
        
        zyRateLimitPortPeakState OBJECT-TYPE
        SYNTAX  EnabledStatus
        MAX-ACCESS  read-write
        STATUS  current
        DESCRIPTION
			"Enabled/Disabled ingress peak rate limiting on the specified port."
        ::= { zyxelRateLimitPortEntry 3 }         
        
        zyRateLimitPortPeakRate OBJECT-TYPE
        SYNTAX  INTEGER
        MAX-ACCESS  read-write
        STATUS  current
        DESCRIPTION
			"Specify the maximum bandwidth allowed in kilobits per second (Kbps) for the incoming traffic flow 
			on the specified port."
        ::= { zyxelRateLimitPortEntry 4 }
 
        zyRateLimitPortEgressState OBJECT-TYPE
        SYNTAX  EnabledStatus
        MAX-ACCESS  read-write
        STATUS  current
        DESCRIPTION
			"Enabled/Disabled egress rate limiting  on the specified port."
        ::= { zyxelRateLimitPortEntry 5 }    
        
        zyRateLimitPortEgressRate OBJECT-TYPE
        SYNTAX  INTEGER
        MAX-ACCESS  read-write
        STATUS  current
        DESCRIPTION
			"Specify the maximum bandwidth allowed in kilobits per second (Kbps) for the out-going traffic flow 
			on the specified port."
        ::= { zyxelRateLimitPortEntry 6 }

END
