-- ZyXEL Communications Corporation
-- Private Enterprise MIB definition 
  
-- This file describes the ZyXEL Communications Corporation Enterprise MIB.
-- It contains ZyXEL products OIDs, and common managed objects.


ZYXEL-ROUTER-MIB DEFINITIONS ::= BEGIN

    IMPORTS
	OBJECT-TYPE
		FROM SNMPv2-SMI			-- RFC2578	
		
	MODULE-IDENTITY
		FROM SNMPv2-SMI
	
	EnabledStatus
		FROM  P-BRIDGE-MIB

	esMgmt			
		FROM ZYXEL-ES-SMI;

	zyxelRouter MODULE-IDENTITY
		LAST-UPDATED	"202004090000Z"    
		ORGANIZATION "Enterprise Solution ZyXEL"     
		CONTACT-INFO
			""	   
		DESCRIPTION
			"The subtree for zyxel router"
		::= { esMgmt 113 }
		
	zyxelRouterIpRouteFailover	     	OBJECT IDENTIFIER ::= { zyxelRouter 2 }
	zyxelRouterIpRouteFailoverSetup	     OBJECT IDENTIFIER ::= { zyxelRouterIpRouteFailover 1 }
    
	zyRouterIpRouteFailoverState OBJECT-TYPE
	SYNTAX  EnabledStatus
	MAX-ACCESS  read-write
	STATUS  current
	DESCRIPTION
					"Enable/Disable IP Route Failover."
	::= { zyxelRouterIpRouteFailoverSetup 1 }

END
