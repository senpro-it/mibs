-- ArubaOS 8.11.0.1_85785
 WLSX-TRAP-MIB DEFINITIONS ::= BEGIN

	IMPORTS
		MODULE-IDENTITY,
		OBJECT-TYPE,
		snmpModules,
		Integer32,
		Counter32,
		IpAddress,
		TimeTicks,
		NOTIFICATION-TYPE
			FROM SNMPv2-SMI

		TEXTUAL-CONVENTION,
		TDomain,
		DisplayString,
		PhysAddress,
		TAddress,
		TimeInterval,
		RowStatus,
		StorageType,
		TestAndIncr,
		MacAddress,
		DateAndTime,
		TruthValue
			FROM SNMPv2-TC

		OBJECT-GROUP
			FROM SNMPv2-CONF
		wlsrEnterpriseMibModules
			FROM ARUBA-MIB
		ArubaFrameType,
		ArubaAddressType,
		ArubaEnableValue,
		ArubaOperStateValue,
		ArubaBlackListReason,
		ArubaDBType,
		ArubaVrrpState,
		ArubaSwitchRole,
		ArubaAuthenticationMethods,
		ArubaConfigurationState,
		ArubaConfigurationChangeType,
		ArubaHTExtChannel,
		ArubaAccessPointMode,
		ArubaAccessPointMode,
		ArubaARMChangeReason,
		ArubaHTExtChannel,
		ArubaConfigurationChangeType,
		ArubaAPMasterStatus,
		ArubaStationType,
		ArubaThresholdResourceType,
		ArubaStackState,
		ArubaStackState,
		ArubaStackChangeEvent,
		ArubaStackIfTopoJoined,
		InterfaceIndex,
		ArubaIfState,
		ArubaIfStateChangeReason,
		ArubaAPUplinkType,
		ArubaAPUplinkType,
		ArubaAPUplinkChangeReason,
		ArubaPortalServerDownReason,
		ArubaPhyType,
		ArubaHTMode,
		ArubaDenyListReason,
		ArubaAPConductorStatus,
		ArubaPhyType,
		ArubaHTMode
			FROM ARUBA-TC;

	wlsrTrapMIB MODULE-IDENTITY		LAST-UPDATED "2212141736Z"
		ORGANIZATION "Aruba, a Hewlett Packard Enterprise company"
		CONTACT-INFO
			"Postal:		3333 Scott Blvd,
				       		Santa Clara, CA 95054
			E-mail:     aruba-ext-eng-reg@hpe.com
			Phone:      +1 408 227 4500"
		DESCRIPTION
			"This MIB defines the Traps generated by the switch.
			"
		REVISION        "2212141736Z"
		DESCRIPTION
			"The initial revision."
		::= { wlsrEnterpriseMibModules 11 }

-- wlsrTrapsGroup
-- This group defines all the traps generated by the switch.

	wlsxTrapsGroup         	OBJECT IDENTIFIER ::= { wlsrTrapMIB 1 }

--Trap Object Group contains objects used in the traps.

	wlsxTrapObjectsGroup         	OBJECT IDENTIFIER ::= { wlsxTrapsGroup 1 }

--Trap Definitions Group contains Traps definitions.

	wlsxTrapDefinitionsGroup      OBJECT IDENTIFIER ::= { wlsxTrapsGroup 2 }

-- Definition of Objects used in the traps

	wlsxTrapAPMacAddress OBJECT-TYPE
		SYNTAX		MacAddress
		MAX-ACCESS	accessible-for-notify
		STATUS		current
		DESCRIPTION
			"			
            This object is used in the traps to indicate 
            the wired MAC address of an access point, for which the trap is being raised.
        			"
	::= {wlsxTrapObjectsGroup 1 }

	wlsxTrapAPIpAddress OBJECT-TYPE
		SYNTAX		IpAddress
		MAX-ACCESS	accessible-for-notify
		STATUS		current
		DESCRIPTION
			"			
            This object is used in the traps to indicate 
            the IP address of an access point, for which the trap is being raised.
        			"
	::= {wlsxTrapObjectsGroup 2 }

	wlsxTrapAPBSSID OBJECT-TYPE
		SYNTAX		MacAddress
		MAX-ACCESS	accessible-for-notify
		STATUS		current
		DESCRIPTION
			"			
            This object is used in the traps to indicate the BSSID of the
            access point, for which the trap is being raised.
        			"
	::= {wlsxTrapObjectsGroup 3 }

	wlsxTrapEssid OBJECT-TYPE
		SYNTAX		DisplayString(SIZE(0..64))
		MAX-ACCESS	accessible-for-notify
		STATUS		current
		DESCRIPTION
			"			
          This object is used in the traps to indicate the SSID of the
          access point, for which the trap is being raised.
        			"
	::= {wlsxTrapObjectsGroup 4 }

	wlsxTrapTargetAPBSSID OBJECT-TYPE
		SYNTAX		MacAddress
		MAX-ACCESS	accessible-for-notify
		STATUS		current
		DESCRIPTION
			"			
            This object is used in the traps to indicate the BSSID of the
            access point, for which we are raising the trap. If an
            Air Monitor is sending the trap then this will indicate
            AP. If an access point is sending the trap, then it will point
            to itself.
        			"
	::= {wlsxTrapObjectsGroup 5 }

	wlsxTrapTargetAPSSID OBJECT-TYPE
		SYNTAX		DisplayString(SIZE(0..64))
		MAX-ACCESS	accessible-for-notify
		STATUS		current
		DESCRIPTION
			"			
          This object is used in the traps to indicate the SSID of the
          access point, for which the trap is being raised. If an
          Air Monitor is sending the trap then this will indicate
          AP. If an access point is sending the trap, then it will point
          to itself.
        			"
	::= {wlsxTrapObjectsGroup 6 }

	wlsxTrapTargetAPChannel OBJECT-TYPE
		SYNTAX		Integer32
		MAX-ACCESS	accessible-for-notify
		STATUS		current
		DESCRIPTION
			"			
          This object is used in the traps to indicate the channel of the
          access point, for which the trap is being raised. If an
          air monitor is sending the trap then this will indicate
          AP. If an access point is sending the trap, then it will point
          to itself.
        			"
	::= {wlsxTrapObjectsGroup 7 }

	wlsxTrapNodeMac OBJECT-TYPE
		SYNTAX		MacAddress
		MAX-ACCESS	accessible-for-notify
		STATUS		current
		DESCRIPTION
			"			
          This object is used in the traps to indicate the MAC address of
          a node.
        			"
	::= {wlsxTrapObjectsGroup 8 }

	wlsxTrapSourceMac OBJECT-TYPE
		SYNTAX		MacAddress
		MAX-ACCESS	accessible-for-notify
		STATUS		current
		DESCRIPTION
			"			
          This object is used in the traps to indicate the MAC address of
          the source.
        			"
	::= {wlsxTrapObjectsGroup 9 }

	wlsxReceiverMac OBJECT-TYPE
		SYNTAX		MacAddress
		MAX-ACCESS	accessible-for-notify
		STATUS		current
		DESCRIPTION
			"			
          This object is used in the traps to indicate the MAC address of
          the receiver.
        			"
	::= {wlsxTrapObjectsGroup 10 }

	wlsxTrapTransmitterMac OBJECT-TYPE
		SYNTAX		MacAddress
		MAX-ACCESS	accessible-for-notify
		STATUS		current
		DESCRIPTION
			"			
          This object is used in the traps to indicate the MAC address of
          the transmitter.
        			"
	::= {wlsxTrapObjectsGroup 11 }

	wlsxTrapReceiverMac OBJECT-TYPE
		SYNTAX		MacAddress
		MAX-ACCESS	accessible-for-notify
		STATUS		current
		DESCRIPTION
			"			
          This object is used in the traps to indicate the MAC address of
          the receiver.
        			"
	::= {wlsxTrapObjectsGroup 12 }

	wlsxTrapSnr OBJECT-TYPE
		SYNTAX		Integer32
		MAX-ACCESS	accessible-for-notify
		STATUS		current
		DESCRIPTION
			"			
          This object is used in the traps to indicate the Signal to Noise
          ratio.
        			"
	::= {wlsxTrapObjectsGroup 13 }

	wlsxTrapSignatureName OBJECT-TYPE
		SYNTAX		DisplayString(SIZE(0..64))
		MAX-ACCESS	accessible-for-notify
		STATUS		current
		DESCRIPTION
			"			
          This object is used in the traps to indicate the Signature Name.
        			"
	::= {wlsxTrapObjectsGroup 14 }

	wlsxTrapFrameType OBJECT-TYPE
		SYNTAX		ArubaFrameType
		MAX-ACCESS	accessible-for-notify
		STATUS		current
		DESCRIPTION
			"			
          This object is used in the traps to indicate the Frame Type
        			"
	::= {wlsxTrapObjectsGroup 15 }

	wlsxTrapAddressType OBJECT-TYPE
		SYNTAX		ArubaAddressType
		MAX-ACCESS	accessible-for-notify
		STATUS		current
		DESCRIPTION
			"			
          This object is used in the traps to indicate the Address type.
        			"
	::= {wlsxTrapObjectsGroup 16 }

	wlsxTrapAPLocation OBJECT-TYPE
		SYNTAX		DisplayString(SIZE(0..64))
		MAX-ACCESS	accessible-for-notify
		STATUS		current
		DESCRIPTION
			"			
          This object is used in the traps to indicate the Location of the AP.
        			"
	::= {wlsxTrapObjectsGroup 17 }

	wlsxTrapAPChannel OBJECT-TYPE
		SYNTAX		Integer32
		MAX-ACCESS	accessible-for-notify
		STATUS		current
		DESCRIPTION
			"			
          This object is used in the traps to indicate the Current Channel.
        			"
	::= {wlsxTrapObjectsGroup 18 }

	wlsxTrapAPTxPower OBJECT-TYPE
		SYNTAX		Integer32
		MAX-ACCESS	accessible-for-notify
		STATUS		current
		DESCRIPTION
			"			
          This object is used in the traps to indicate the AP Transmit Power.
        			"
	::= {wlsxTrapObjectsGroup 19 }

	wlsxTrapMatchedMac OBJECT-TYPE
		SYNTAX		MacAddress
		MAX-ACCESS	accessible-for-notify
		STATUS		current
		DESCRIPTION
			"			
            This object is used in the traps to indicate the MAC address
        			"
	::= {wlsxTrapObjectsGroup 20 }

	wlsxTrapMatchedIp OBJECT-TYPE
		SYNTAX		IpAddress
		MAX-ACCESS	accessible-for-notify
		STATUS		current
		DESCRIPTION
			"			
            This object is used in the traps to indicate the IP address
        			"
	::= {wlsxTrapObjectsGroup 21 }

	wlsxTrapRogueIfoURL OBJECT-TYPE
		SYNTAX		DisplayString(SIZE(0..64))
		MAX-ACCESS	accessible-for-notify
		STATUS		current
		DESCRIPTION
			"			
            This object is used to point to the WEBUI Rogue AP information URL.
        			"
	::= {wlsxTrapObjectsGroup 22 }

	wlsxTrapVlanId OBJECT-TYPE
		SYNTAX		Integer32
		MAX-ACCESS	accessible-for-notify
		STATUS		current
		DESCRIPTION
			"			
            This object is used in the traps to indicate the VLAN Id.
        			"
	::= {wlsxTrapObjectsGroup 23 }

	wlsxTrapAdminStatus OBJECT-TYPE
		SYNTAX		ArubaEnableValue
		MAX-ACCESS	accessible-for-notify
		STATUS		current
		DESCRIPTION
			"			
            This object is used in the traps to indicate the admin status of
            VLAN.
        			"
	::= {wlsxTrapObjectsGroup 24 }

	wlsxTrapOperStatus OBJECT-TYPE
		SYNTAX		ArubaOperStateValue
		MAX-ACCESS	accessible-for-notify
		STATUS		current
		DESCRIPTION
			"			
            This object is used in the traps to indicate the admin status of
            VLAN.
        			"
	::= {wlsxTrapObjectsGroup 25 }

	wlsxTrapAuthServerName OBJECT-TYPE
		SYNTAX		DisplayString(SIZE(0..64))
		MAX-ACCESS	accessible-for-notify
		STATUS		current
		DESCRIPTION
			"			
            This object is used in the traps to indicate the
            Authentication Server used for Authentication.
        			"
	::= {wlsxTrapObjectsGroup 26 }

	wlsxTrapAuthServerTimeout OBJECT-TYPE
		SYNTAX		Integer32
		MAX-ACCESS	accessible-for-notify
		STATUS		current
		DESCRIPTION
			"			
            This object is used in the traps to indicate the
            Authentication Server Timeout.
        			"
	::= {wlsxTrapObjectsGroup 27 }

	wlsxTrapCardSlot OBJECT-TYPE
		SYNTAX		Integer32
		MAX-ACCESS	accessible-for-notify
		STATUS		current
		DESCRIPTION
			"			
            This object is used in the traps to indicate the
           Slot in which this card is present.
        			"
	::= {wlsxTrapObjectsGroup 28 }

	wlsxTrapTemperatureValue OBJECT-TYPE
		SYNTAX		DisplayString(SIZE(0..64))
		MAX-ACCESS	accessible-for-notify
		STATUS		current
		DESCRIPTION
			"			
            This object is used in the traps to indicate the
            Temperature Value.
        			"
	::= {wlsxTrapObjectsGroup 29 }

	wlsxTrapProcessName OBJECT-TYPE
		SYNTAX		DisplayString(SIZE(0..64))
		MAX-ACCESS	accessible-for-notify
		STATUS		current
		DESCRIPTION
			"			
            This object is used in the traps to indicate the
            Process name.
        			"
	::= {wlsxTrapObjectsGroup 30 }

	wlsxTrapFanNumber OBJECT-TYPE
		SYNTAX		Integer32
		MAX-ACCESS	accessible-for-notify
		STATUS		current
		DESCRIPTION
			"			
            This object is used in the traps to indicate the
            Fan Number.
        			"
	::= {wlsxTrapObjectsGroup 31 }

	wlsxTrapVoltageType OBJECT-TYPE
		SYNTAX		DisplayString(SIZE(0..64))
		MAX-ACCESS	accessible-for-notify
		STATUS		current
		DESCRIPTION
			"			
            This object is used in the traps to indicate the
            type of Voltage.
        			"
	::= {wlsxTrapObjectsGroup 32 }

	wlsxTrapVoltageValue OBJECT-TYPE
		SYNTAX		DisplayString(SIZE(0..64))
		MAX-ACCESS	accessible-for-notify
		STATUS		current
		DESCRIPTION
			"			
            This object is used in the traps to indicate the
            voltage value in Float.
        			"
	::= {wlsxTrapObjectsGroup 33 }

	wlsxTrapStationBlackListReason OBJECT-TYPE
		SYNTAX		ArubaBlackListReason
		MAX-ACCESS	accessible-for-notify
		STATUS		obsolete
		DESCRIPTION
			"			
            The Reason for which a station is black listed.
            **NOTE: this trap is obsoleted and replaced by
            wlsxTrapStationDenyListReason
        			"
	::= {wlsxTrapObjectsGroup 34 }

	wlsxTrapSpoofedIpAddress OBJECT-TYPE
		SYNTAX		IpAddress
		MAX-ACCESS	accessible-for-notify
		STATUS		current
		DESCRIPTION
			"			
            This object is used in a trap to identify a spoofed IP address.
        			"
	::= {wlsxTrapObjectsGroup 35 }

	wlsxTrapSpoofedOldPhyAddress OBJECT-TYPE
		SYNTAX		MacAddress
		MAX-ACCESS	accessible-for-notify
		STATUS		current
		DESCRIPTION
			"			
            This object is used in a trap to identify an old MAC address.
        			"
	::= {wlsxTrapObjectsGroup 36 }

	wlsxTrapSpoofedNewPhyAddress OBJECT-TYPE
		SYNTAX		MacAddress
		MAX-ACCESS	accessible-for-notify
		STATUS		current
		DESCRIPTION
			"			
            This object is used in a trap to identify a New MAC address.
        			"
	::= {wlsxTrapObjectsGroup 37 }

	wlsxTrapDBName OBJECT-TYPE
		SYNTAX		DisplayString(SIZE(0..64))
		MAX-ACCESS	accessible-for-notify
		STATUS		current
		DESCRIPTION
			"			
            This object is used in a trap to identify name of the database.
        			"
	::= {wlsxTrapObjectsGroup 38 }

	wlsxTrapDBUserName OBJECT-TYPE
		SYNTAX		DisplayString(SIZE(0..64))
		MAX-ACCESS	accessible-for-notify
		STATUS		current
		DESCRIPTION
			"			
            This object is used in a trap to identify name of the database user.
        			"
	::= {wlsxTrapObjectsGroup 39 }

	wlsxTrapDBIpAddress OBJECT-TYPE
		SYNTAX		DisplayString(SIZE(0..64))
		MAX-ACCESS	accessible-for-notify
		STATUS		current
		DESCRIPTION
			"			
            This object is used in a trap to identify the IpAddress of the 
            Database.
        			"
	::= {wlsxTrapObjectsGroup 40 }

	wlsxTrapDBType OBJECT-TYPE
		SYNTAX		ArubaDBType
		MAX-ACCESS	accessible-for-notify
		STATUS		current
		DESCRIPTION
			"			
            This object is used in a trap to identify the port of the user.
        			"
	::= {wlsxTrapObjectsGroup 41 }

	wlsxTrapVrrpID OBJECT-TYPE
		SYNTAX		Integer32
		MAX-ACCESS	accessible-for-notify
		STATUS		current
		DESCRIPTION
			"			
            This object contains the Virtual Router Identifier.
        			"
	::= {wlsxTrapObjectsGroup 42 }

	wlsxTrapVrrpMasterIp OBJECT-TYPE
		SYNTAX		IpAddress
		MAX-ACCESS	accessible-for-notify
		STATUS		current
		DESCRIPTION
			"			
            This object contains the Master IP address.
        			"
	::= {wlsxTrapObjectsGroup 43 }

	wlsxTrapVrrpOperState OBJECT-TYPE
		SYNTAX		ArubaVrrpState
		MAX-ACCESS	accessible-for-notify
		STATUS		current
		DESCRIPTION
			"			
            This object represents the VRRP Operational state.
        			"
	::= {wlsxTrapObjectsGroup 44 }

	wlsxTrapESIServerGrpName OBJECT-TYPE
		SYNTAX		DisplayString(SIZE(0..64))
		MAX-ACCESS	accessible-for-notify
		STATUS		current
		DESCRIPTION
			"			
            This object represents the External Services Interface (ESI) Server
            Group name
        			"
	::= {wlsxTrapObjectsGroup 45 }

	wlsxTrapESIServerName OBJECT-TYPE
		SYNTAX		DisplayString(SIZE(0..64))
		MAX-ACCESS	accessible-for-notify
		STATUS		current
		DESCRIPTION
			"			
            This object represents the External Services Interface (ESI) Server
            Name
        			"
	::= {wlsxTrapObjectsGroup 46 }

	wlsxTrapESIServerIpAddress OBJECT-TYPE
		SYNTAX		IpAddress
		MAX-ACCESS	accessible-for-notify
		STATUS		current
		DESCRIPTION
			"			
            This object represents the External Services Interface (ESI) Server
            IP address
        			"
	::= {wlsxTrapObjectsGroup 47 }

	wlsxTrapLicenseDaysRemaining OBJECT-TYPE
		SYNTAX		Integer32
		MAX-ACCESS	accessible-for-notify
		STATUS		current
		DESCRIPTION
			"			
            This object represents number of the days remaining prior to a 
            license expiry.
        			"
	::= {wlsxTrapObjectsGroup 48 }

	wlsxTrapSwitchIp OBJECT-TYPE
		SYNTAX		IpAddress
		MAX-ACCESS	accessible-for-notify
		STATUS		current
		DESCRIPTION
			"			
            This object represents the controller IP address. 
        			"
	::= {wlsxTrapObjectsGroup 49 }

	wlsxTrapSwitchRole OBJECT-TYPE
		SYNTAX		ArubaSwitchRole
		MAX-ACCESS	accessible-for-notify
		STATUS		current
		DESCRIPTION
			"			
            This object represents the Role of the controller. 
        			"
	::= {wlsxTrapObjectsGroup 50 }

	wlsxTrapUserIpAddress OBJECT-TYPE
		SYNTAX		IpAddress
		MAX-ACCESS	accessible-for-notify
		STATUS		current
		DESCRIPTION
			"			
            This object represents IP address of the User.
        			"
	::= {wlsxTrapObjectsGroup 51 }

	wlsxTrapUserPhyAddress OBJECT-TYPE
		SYNTAX		MacAddress
		MAX-ACCESS	accessible-for-notify
		STATUS		current
		DESCRIPTION
			"			
            This object represents MAC address of the User.
        			"
	::= {wlsxTrapObjectsGroup 52 }

	wlsxTrapUserName OBJECT-TYPE
		SYNTAX		DisplayString(SIZE(0..64))
		MAX-ACCESS	accessible-for-notify
		STATUS		current
		DESCRIPTION
			"			
            This object represents the user name.
        			"
	::= {wlsxTrapObjectsGroup 53 }

	wlsxTrapUserRole OBJECT-TYPE
		SYNTAX		DisplayString(SIZE(0..64))
		MAX-ACCESS	accessible-for-notify
		STATUS		current
		DESCRIPTION
			"			
            This object represents the Authentication method of the user.
        			"
	::= {wlsxTrapObjectsGroup 54 }

	wlsxTrapUserAuthenticationMethod OBJECT-TYPE
		SYNTAX		ArubaAuthenticationMethods
		MAX-ACCESS	accessible-for-notify
		STATUS		current
		DESCRIPTION
			"			
            This object represents the Authentication method of the user.
        			"
	::= {wlsxTrapObjectsGroup 55 }

	wlsxTrapAPRadioNumber OBJECT-TYPE
		SYNTAX		Integer32
		MAX-ACCESS	accessible-for-notify
		STATUS		current
		DESCRIPTION
			"			
            This object represents the radio number.
        			"
	::= {wlsxTrapObjectsGroup 56 }

	wlsxTrapRogueInfoURL OBJECT-TYPE
		SYNTAX		DisplayString(SIZE(0..64))
		MAX-ACCESS	accessible-for-notify
		STATUS		current
		DESCRIPTION
			"			
			This object is used to point to the WEBGUI Rogue AP information 
			URL.
        			"
	::= {wlsxTrapObjectsGroup 57 }

	wlsxTrapInterferingAPInfoURL OBJECT-TYPE
		SYNTAX		DisplayString(SIZE(0..64))
		MAX-ACCESS	accessible-for-notify
		STATUS		current
		DESCRIPTION
			"			
			This object is used to point to the WEBGUI Rogue interfering 
			AP information URL.
        			"
	::= {wlsxTrapObjectsGroup 58 }

	wlsxTrapPortNumber OBJECT-TYPE
		SYNTAX		Integer32
		MAX-ACCESS	accessible-for-notify
		STATUS		current
		DESCRIPTION
			"			
            This object is used in the traps to indicate the
           port number.
        			"
	::= {wlsxTrapObjectsGroup 59 }

	wlsxTrapTime OBJECT-TYPE
		SYNTAX		DateAndTime
		MAX-ACCESS	accessible-for-notify
		STATUS		current
		DESCRIPTION
			"			
            This object is used in all the enterprise traps to indicate the
           the time when the trap is generated on the controller.
        			"
	::= {wlsxTrapObjectsGroup 60 }

	wlsxTrapHostIp OBJECT-TYPE
		SYNTAX		IpAddress
		MAX-ACCESS	accessible-for-notify
		STATUS		current
		DESCRIPTION
			"			
            This object represents the Trap host. 
        			"
	::= {wlsxTrapObjectsGroup 61 }

	wlsxTrapHostPort OBJECT-TYPE
		SYNTAX		Integer32
		MAX-ACCESS	accessible-for-notify
		STATUS		current
		DESCRIPTION
			"			
            This object represents the Trap host port. 
        			"
	::= {wlsxTrapObjectsGroup 62 }

	wlsxTrapConfigurationId OBJECT-TYPE
		SYNTAX		Integer32
		MAX-ACCESS	accessible-for-notify
		STATUS		current
		DESCRIPTION
			"			
            This object represents the ID of the configuration, to be used in traps.
        			"
	::= {wlsxTrapObjectsGroup 63 }

	wlsxTrapCTSURL OBJECT-TYPE
		SYNTAX		DisplayString(SIZE(0..64))
		MAX-ACCESS	accessible-for-notify
		STATUS		current
		DESCRIPTION
			"			
            This object represents the URL from which the transfer should happen.
        			"
	::= {wlsxTrapObjectsGroup 64 }

	wlsxTrapCTSTransferType OBJECT-TYPE
		SYNTAX		DisplayString(SIZE(0..64))
		MAX-ACCESS	accessible-for-notify
		STATUS		current
		DESCRIPTION
			"			
            This object represents  the transfer type, upload or download.
        			"
	::= {wlsxTrapObjectsGroup 65 }

	wlsxTrapConfigurationState OBJECT-TYPE
		SYNTAX		ArubaConfigurationState
		MAX-ACCESS	accessible-for-notify
		STATUS		current
		DESCRIPTION
			"			
            This object represents state of the configuration transfer.
        			"
	::= {wlsxTrapObjectsGroup 66 }

	wlsxTrapUpdateFailureReason OBJECT-TYPE
		SYNTAX		DisplayString(SIZE(0..64))
		MAX-ACCESS	accessible-for-notify
		STATUS		current
		DESCRIPTION
			"			
            This object represents the reason for the update failure.
        			"
	::= {wlsxTrapObjectsGroup 67 }

	wlsxTrapUpdateFailedObj OBJECT-TYPE
		SYNTAX		DisplayString(SIZE(0..64))
		MAX-ACCESS	accessible-for-notify
		STATUS		current
		DESCRIPTION
			"			
            This variable represents the AMAPI object which is the reason for the the update failure.
        			"
	::= {wlsxTrapObjectsGroup 68 }

	wlsxTrapTableEntryChangeType OBJECT-TYPE
		SYNTAX		ArubaConfigurationChangeType
		MAX-ACCESS	accessible-for-notify
		STATUS		current
		DESCRIPTION
			"			
            This object represents type of the configuration change. 
        			"
	::= {wlsxTrapObjectsGroup 69 }

	wlsxTrapGlobalConfigObj OBJECT-TYPE
		SYNTAX		DisplayString(SIZE(0..64))
		MAX-ACCESS	accessible-for-notify
		STATUS		current
		DESCRIPTION
			"			
            This variable represents the AMAPI object corresponding to the global configuration change.
        			"
	::= {wlsxTrapObjectsGroup 70 }

	wlsxTrapTableGenNumber OBJECT-TYPE
		SYNTAX		Integer32
		MAX-ACCESS	accessible-for-notify
		STATUS		current
		DESCRIPTION
			"			
            This object represents generation number of a table. Used in the MMS, to keep track of the table content changes.
        			"
	::= {wlsxTrapObjectsGroup 71 }

	wlsxTrapLicenseId OBJECT-TYPE
		SYNTAX		Integer32
		MAX-ACCESS	accessible-for-notify
		STATUS		current
		DESCRIPTION
			"			
            This object is used in the traps to indicate the license ID.
        			"
	::= {wlsxTrapObjectsGroup 72 }

	wlsxTrapConfidenceLevel OBJECT-TYPE
		SYNTAX		Integer32
		MAX-ACCESS	accessible-for-notify
		STATUS		current
		DESCRIPTION
			"			
            This object is used in the traps to indicate the Confidence Level as a percentage
        			"
	::= {wlsxTrapObjectsGroup 73 }

	wlsxTrapMissingLicenses OBJECT-TYPE
		SYNTAX		DisplayString(SIZE(0..64))
		MAX-ACCESS	accessible-for-notify
		STATUS		current
		DESCRIPTION
			"			
            This variable indicates any licenses that are not present during a configuration update
        			"
	::= {wlsxTrapObjectsGroup 74 }

	wlsxVoiceCurrentNumCdr OBJECT-TYPE
		SYNTAX		Integer32
		MAX-ACCESS	accessible-for-notify
		STATUS		current
		DESCRIPTION
			"			
            This object represents  the number of CDRs in buffer.
        			"
	::= {wlsxTrapObjectsGroup 75 }

	wlsxTrapTunnelId OBJECT-TYPE
		SYNTAX		Integer32
		MAX-ACCESS	accessible-for-notify
		STATUS		current
		DESCRIPTION
			"			
            This Object represents the tunnel ID.
        			"
	::= {wlsxTrapObjectsGroup 76 }

	wlsxTrapTunnelStatus OBJECT-TYPE
		SYNTAX		Integer32
		MAX-ACCESS	accessible-for-notify
		STATUS		current
		DESCRIPTION
			"			
            This Object represents the tunnel Status.
        			"
	::= {wlsxTrapObjectsGroup 77 }

	wlsxTrapTunnelUpReason OBJECT-TYPE
		SYNTAX		DisplayString(SIZE(0..64))
		MAX-ACCESS	accessible-for-notify
		STATUS		current
		DESCRIPTION
			"			
            This Object represents the tunnel up reason.
        			"
	::= {wlsxTrapObjectsGroup 78 }

	wlsxTrapTunnelDownReason OBJECT-TYPE
		SYNTAX		DisplayString(SIZE(0..64))
		MAX-ACCESS	accessible-for-notify
		STATUS		current
		DESCRIPTION
			"			
            This Object represents the tunnel down reason.
        			"
	::= {wlsxTrapObjectsGroup 79 }

	wlsxTrapApSerialNumber OBJECT-TYPE
		SYNTAX		DisplayString(SIZE(0..64))
		MAX-ACCESS	accessible-for-notify
		STATUS		current
		DESCRIPTION
			"			
          This object represents the AP Serial Number.
        			"
	::= {wlsxTrapObjectsGroup 80 }

	wlsxTrapTimeStr OBJECT-TYPE
		SYNTAX		DisplayString(SIZE(0..64))
		MAX-ACCESS	accessible-for-notify
		STATUS		current
		DESCRIPTION
			"			
          This object represents the Time in String format.
        			"
	::= {wlsxTrapObjectsGroup 81 }

	wlsxTrapMasterIp OBJECT-TYPE
		SYNTAX		IpAddress
		MAX-ACCESS	accessible-for-notify
		STATUS		obsolete
		DESCRIPTION
			"			
            This object represents the master IP address. 
        			"
	::= {wlsxTrapObjectsGroup 82 }

	wlsxTrapLocalIp OBJECT-TYPE
		SYNTAX		IpAddress
		MAX-ACCESS	accessible-for-notify
		STATUS		obsolete
		DESCRIPTION
			"			
            This object represents the Local IP address.
        			"
	::= {wlsxTrapObjectsGroup 83 }

	wlsxTrapMasterName OBJECT-TYPE
		SYNTAX		DisplayString(SIZE(0..64))
		MAX-ACCESS	accessible-for-notify
		STATUS		obsolete
		DESCRIPTION
			"			
            This object represents the master controller name.
        			"
	::= {wlsxTrapObjectsGroup 84 }

	wlsxTrapLocalName OBJECT-TYPE
		SYNTAX		DisplayString(SIZE(0..64))
		MAX-ACCESS	accessible-for-notify
		STATUS		obsolete
		DESCRIPTION
			"			
            This object represents the local controller name.
        			"
	::= {wlsxTrapObjectsGroup 85 }

	wlsxTrapPrimaryControllerIp OBJECT-TYPE
		SYNTAX		IpAddress
		MAX-ACCESS	accessible-for-notify
		STATUS		current
		DESCRIPTION
			"			
            This object represents the IP address of the AP's primary controller.
        			"
	::= {wlsxTrapObjectsGroup 86 }

	wlsxTrapBackupControllerIp OBJECT-TYPE
		SYNTAX		IpAddress
		MAX-ACCESS	accessible-for-notify
		STATUS		current
		DESCRIPTION
			"			
            This object represents the IP address of the AP's backup controller.
        			"
	::= {wlsxTrapObjectsGroup 87 }

	wlsxTrapSpoofedFrameType OBJECT-TYPE
		SYNTAX		DisplayString(SIZE(0..64))
		MAX-ACCESS	accessible-for-notify
		STATUS		current
		DESCRIPTION
			"			
          This object is used in the traps to indicate the Spoofed Frame Type
        			"
	::= {wlsxTrapObjectsGroup 88 }

	wlsxTrapAssociationType OBJECT-TYPE
		SYNTAX		DisplayString(SIZE(0..64))
		MAX-ACCESS	accessible-for-notify
		STATUS		current
		DESCRIPTION
			"			
          This object is used in the traps to indicate the type of association
        			"
	::= {wlsxTrapObjectsGroup 89 }

	wlsxTrapDeviceIpAddress OBJECT-TYPE
		SYNTAX		IpAddress
		MAX-ACCESS	accessible-for-notify
		STATUS		current
		DESCRIPTION
			"			
            This object represents the IP address of a device seen by an AP.
        			"
	::= {wlsxTrapObjectsGroup 90 }

	wlsxTrapDeviceMac OBJECT-TYPE
		SYNTAX		MacAddress
		MAX-ACCESS	accessible-for-notify
		STATUS		current
		DESCRIPTION
			"			
          This object represents the MAC address of a device seen by an AP.
        			"
	::= {wlsxTrapObjectsGroup 91 }

	wlsxTrapVcIpAddress OBJECT-TYPE
		SYNTAX		IpAddress
		MAX-ACCESS	accessible-for-notify
		STATUS		current
		DESCRIPTION
			"			
            This object represents the Ip Address of a Voice client.
        			"
	::= {wlsxTrapObjectsGroup 92 }

	wlsxTrapVcMacAddress OBJECT-TYPE
		SYNTAX		MacAddress
		MAX-ACCESS	accessible-for-notify
		STATUS		current
		DESCRIPTION
			"			
            This object represents the MAC address of a Voice client.
        			"
	::= {wlsxTrapObjectsGroup 93 }

	wlsxTrapAPName OBJECT-TYPE
		SYNTAX		DisplayString(SIZE(0..64))
		MAX-ACCESS	accessible-for-notify
		STATUS		current
		DESCRIPTION
			"			
          This object is used in the traps to indicate the Name of the AP.
        			"
	::= {wlsxTrapObjectsGroup 94 }

	wlsxTrapApMode OBJECT-TYPE
		SYNTAX		Integer32
		MAX-ACCESS	accessible-for-notify
		STATUS		current
		DESCRIPTION
			"			
            This Object represents the AP Mode.
        			"
	::= {wlsxTrapObjectsGroup 95 }

	wlsxTrapAPPrevChannel OBJECT-TYPE
		SYNTAX		Integer32
		MAX-ACCESS	accessible-for-notify
		STATUS		current
		DESCRIPTION
			"			
          This object is used in the traps to indicate the Previous Channel.
        			"
	::= {wlsxTrapObjectsGroup 96 }

	wlsxTrapAPPrevChannelSec OBJECT-TYPE
		SYNTAX		ArubaHTExtChannel
		MAX-ACCESS	accessible-for-notify
		STATUS		current
		DESCRIPTION
			"			
          This object is used in the traps to indicate the Previous Secondary Channel.
        			"
	::= {wlsxTrapObjectsGroup 97 }

	wlsxTrapAPPrevTxPower OBJECT-TYPE
		SYNTAX		Integer32
		MAX-ACCESS	accessible-for-notify
		STATUS		current
		DESCRIPTION
			"			
          This object is used in the traps to indicate previous AP Transmit Power.
        			"
	::= {wlsxTrapObjectsGroup 98 }

	wlsxTrapAPCurMode OBJECT-TYPE
		SYNTAX		ArubaAccessPointMode
		MAX-ACCESS	accessible-for-notify
		STATUS		current
		DESCRIPTION
			"			
            This Object represents the APs Current Mode.
        			"
	::= {wlsxTrapObjectsGroup 99 }

	wlsxTrapAPPrevMode OBJECT-TYPE
		SYNTAX		ArubaAccessPointMode
		MAX-ACCESS	accessible-for-notify
		STATUS		current
		DESCRIPTION
			"			
            This Object represents the APs Previous Mode.
        			"
	::= {wlsxTrapObjectsGroup 100 }

	wlsxTrapAPARMChangeReason OBJECT-TYPE
		SYNTAX		ArubaARMChangeReason
		MAX-ACCESS	accessible-for-notify
		STATUS		current
		DESCRIPTION
			"			
            This Object represents the APs Previous Mode.
        			"
	::= {wlsxTrapObjectsGroup 101 }

	wlsxTrapAPChannelSec OBJECT-TYPE
		SYNTAX		ArubaHTExtChannel
		MAX-ACCESS	accessible-for-notify
		STATUS		current
		DESCRIPTION
			"			
          This object is used in the traps to indicate the Current Secondary Channel.
        			"
	::= {wlsxTrapObjectsGroup 102 }

	wlsxTrapUserAttributeChangeType OBJECT-TYPE
		SYNTAX		ArubaConfigurationChangeType
		MAX-ACCESS	accessible-for-notify
		STATUS		current
		DESCRIPTION
			"			
            This object represents type of the configuration change. 
        			"
	::= {wlsxTrapObjectsGroup 103 }

	wlsxTrapApControllerIp OBJECT-TYPE
		SYNTAX		IpAddress
		MAX-ACCESS	accessible-for-notify
		STATUS		current
		DESCRIPTION
			"			
            IP address of the controller to which the AP is
            (or was most recently) registered.
        			"
	::= {wlsxTrapObjectsGroup 104 }

	wlsxTrapApMasterStatus OBJECT-TYPE
		SYNTAX		ArubaAPMasterStatus
		MAX-ACCESS	accessible-for-notify
		STATUS		obsolete
		DESCRIPTION
			"			
            Status of the AP as seen by the master when the status changes.
            **NOTE: this object is obsoleted and replaced by
            wlsxTrapApConductorStatus
        			"
	::= {wlsxTrapObjectsGroup 105 }

	wlsxTrapCaName OBJECT-TYPE
		SYNTAX		DisplayString(SIZE(0..64))
		MAX-ACCESS	accessible-for-notify
		STATUS		current
		DESCRIPTION
			"			
            This object is used in the traps to indicate the name of the trustpoint.
        			"
	::= {wlsxTrapObjectsGroup 106 }

	wlsxTrapCrlName OBJECT-TYPE
		SYNTAX		DisplayString(SIZE(0..64))
		MAX-ACCESS	accessible-for-notify
		STATUS		current
		DESCRIPTION
			"			
            This object is used in the traps to indicate the name of the crl.
        			"
	::= {wlsxTrapObjectsGroup 107 }

	wlsxTrapCount OBJECT-TYPE
		SYNTAX		Integer32
		MAX-ACCESS	accessible-for-notify
		STATUS		current
		DESCRIPTION
			"			
            This object represents the number of occurrence of this trap.
        			"
	::= {wlsxTrapObjectsGroup 108 }

	wlsxTrapPowerSupplyNumber OBJECT-TYPE
		SYNTAX		Integer32
		MAX-ACCESS	accessible-for-notify
		STATUS		current
		DESCRIPTION
			"			
            This object represents the power supply number.
        			"
	::= {wlsxTrapObjectsGroup 109 }

	wlsxTrapFanTrayNumber OBJECT-TYPE
		SYNTAX		Integer32
		MAX-ACCESS	accessible-for-notify
		STATUS		current
		DESCRIPTION
			"			
            This object represents the Fan Tray number.
        			"
	::= {wlsxTrapObjectsGroup 110 }

	wlsxTrapClientClassification OBJECT-TYPE
		SYNTAX		ArubaStationType
		MAX-ACCESS	accessible-for-notify
		STATUS		current
		DESCRIPTION
			"			
            This object is used in the traps to indicate the classification of the client.
        			"
	::= {wlsxTrapObjectsGroup 111 }

	wlsxThresholdResourceType OBJECT-TYPE
		SYNTAX		ArubaThresholdResourceType
		MAX-ACCESS	accessible-for-notify
		STATUS		current
		DESCRIPTION
			"			
          This object represents the Threshold alert's Resource Type .
        			"
	::= {wlsxTrapObjectsGroup 112 }

	wlsxThresholdResourceName OBJECT-TYPE
		SYNTAX		DisplayString(SIZE(0..64))
		MAX-ACCESS	accessible-for-notify
		STATUS		current
		DESCRIPTION
			"			
          This object represents the Threshold alert's Resource Name .
        			"
	::= {wlsxTrapObjectsGroup 113 }

	wlsxThresholdValue OBJECT-TYPE
		SYNTAX		Integer32
		MAX-ACCESS	accessible-for-notify
		STATUS		current
		DESCRIPTION
			"			
            This object represents the Threshold alert's set threshold value.
        			"
	::= {wlsxTrapObjectsGroup 114 }

	wlsxResourceValue OBJECT-TYPE
		SYNTAX		Integer32
		MAX-ACCESS	accessible-for-notify
		STATUS		current
		DESCRIPTION
			"			
            This object represents the Threshold alert's actual value.
        			"
	::= {wlsxTrapObjectsGroup 115 }

	wlsxStackPrevSlot OBJECT-TYPE
		SYNTAX		Integer32
		MAX-ACCESS	accessible-for-notify
		STATUS		current
		DESCRIPTION
			"			
            This object specifies the slot number of this stack element prior
            to topology change in stack. A value of -1 indicates that this slot
            was not in Active state of stack prior to topology change.
        			"
	::= {wlsxTrapObjectsGroup 116 }

	wlsxStackCurrentSlot OBJECT-TYPE
		SYNTAX		Integer32
		MAX-ACCESS	accessible-for-notify
		STATUS		current
		DESCRIPTION
			"			
            This object specifies the slot number of this stack element after
            the topology change in stack. A value of -1 indicates that this slot
            is not in Active state of stack after the topology change.
        			"
	::= {wlsxTrapObjectsGroup 117 }

	wlsxStackPrevState OBJECT-TYPE
		SYNTAX		ArubaStackState
		MAX-ACCESS	accessible-for-notify
		STATUS		current
		DESCRIPTION
			"			
            This object specifies the state of this stack element prior to
            topology change in stack.
        			"
	::= {wlsxTrapObjectsGroup 118 }

	wlsxStackCurrentState OBJECT-TYPE
		SYNTAX		ArubaStackState
		MAX-ACCESS	accessible-for-notify
		STATUS		current
		DESCRIPTION
			"			
            This object specifies the state of this stack element
            after topology change in stack.
        			"
	::= {wlsxTrapObjectsGroup 119 }

	wlsxStackChangeEvent OBJECT-TYPE
		SYNTAX		ArubaStackChangeEvent
		MAX-ACCESS	accessible-for-notify
		STATUS		current
		DESCRIPTION
			"			
            This object specifies the event which caused change in topology in
            stack.
        			"
	::= {wlsxTrapObjectsGroup 120 }

	wlsxStackProtoIfTopoJoined OBJECT-TYPE
		SYNTAX		ArubaStackIfTopoJoined
		MAX-ACCESS	accessible-for-notify
		STATUS		current
		DESCRIPTION
			"			
            This object specifies whether an interface has joined the stacking
            topology or left the topology.
        			"
	::= {wlsxTrapObjectsGroup 121 }

	wlsxStackMemberMacAddress OBJECT-TYPE
		SYNTAX		MacAddress
		MAX-ACCESS	accessible-for-notify
		STATUS		current
		DESCRIPTION
			"			
            This object specifies mac-address of this stack element.
        			"
	::= {wlsxTrapObjectsGroup 122 }

	wlsxStackMemberSlotNumber OBJECT-TYPE
		SYNTAX		Integer32
		MAX-ACCESS	accessible-for-notify
		STATUS		current
		DESCRIPTION
			"			
            This object specifies the slot number of this element in stack.
        			"
	::= {wlsxTrapObjectsGroup 123 }

	wlsxStackIfName OBJECT-TYPE
		SYNTAX		DisplayString(SIZE(0..64))
		MAX-ACCESS	accessible-for-notify
		STATUS		current
		DESCRIPTION
			"			
            This object specifies the interface name which is part of stacking
            link connected to other stacking element.
        			"
	::= {wlsxTrapObjectsGroup 124 }

	wlsxTrapLicenseServerDaysRemaining OBJECT-TYPE
		SYNTAX		Integer32
		MAX-ACCESS	accessible-for-notify
		STATUS		current
		DESCRIPTION
			"			
            This object represents number of the days remaining prior to expiry 
            of license limits sent by the server.
        			"
	::= {wlsxTrapObjectsGroup 125 }

	wlsxTrapLicenseClientDaysRemaining OBJECT-TYPE
		SYNTAX		Integer32
		MAX-ACCESS	accessible-for-notify
		STATUS		current
		DESCRIPTION
			"			
            This object represents number of the days remaining prior to expiry 
            of licenses contributed by a license client.
        			"
	::= {wlsxTrapObjectsGroup 126 }

	wlsxIfIndex OBJECT-TYPE
		SYNTAX		InterfaceIndex
		MAX-ACCESS	accessible-for-notify
		STATUS		current
		DESCRIPTION
			"			
            This object specifies the ifIndex.
        			"
	::= {wlsxTrapObjectsGroup 127 }

	wlsxIfState OBJECT-TYPE
		SYNTAX		ArubaIfState
		MAX-ACCESS	accessible-for-notify
		STATUS		current
		DESCRIPTION
			"			
            This object specifies the state of an interface.
        			"
	::= {wlsxTrapObjectsGroup 128 }

	wlsxIfStateChangeReason OBJECT-TYPE
		SYNTAX		ArubaIfStateChangeReason
		MAX-ACCESS	accessible-for-notify
		STATUS		current
		DESCRIPTION
			"			
            This object specifies the reason for interface state change.
        			"
	::= {wlsxTrapObjectsGroup 129 }

	wlsxTrapAPPreviousUplinkType OBJECT-TYPE
		SYNTAX		ArubaAPUplinkType
		MAX-ACCESS	accessible-for-notify
		STATUS		current
		DESCRIPTION
			"			
            This object specifies the up link type for an AP.
        			"
	::= {wlsxTrapObjectsGroup 130 }

	wlsxTrapAPPreviousUplinkActiveTime OBJECT-TYPE
		SYNTAX		TimeTicks
		MAX-ACCESS	accessible-for-notify
		STATUS		current
		DESCRIPTION
			"			
            This object specifies the up link type for an AP.
        			"
	::= {wlsxTrapObjectsGroup 131 }

	wlsxTrapAPActiveUplinkType OBJECT-TYPE
		SYNTAX		ArubaAPUplinkType
		MAX-ACCESS	accessible-for-notify
		STATUS		current
		DESCRIPTION
			"			
            This object specifies the up link type for an AP.
        			"
	::= {wlsxTrapObjectsGroup 132 }

	wlsxTrapAPUplinkChangeReason OBJECT-TYPE
		SYNTAX		ArubaAPUplinkChangeReason
		MAX-ACCESS	accessible-for-notify
		STATUS		current
		DESCRIPTION
			"			
            This object specifies the up link change reason.
        			"
	::= {wlsxTrapObjectsGroup 133 }

	wlsxTrapExpiringCertName OBJECT-TYPE
		SYNTAX		DisplayString(SIZE(0..64))
		MAX-ACCESS	accessible-for-notify
		STATUS		current
		DESCRIPTION
			"			
            This object is used in the traps to indicate the name of the certificate that is expiring in less than 60 days.
        			"
	::= {wlsxTrapObjectsGroup 134 }

	wlsxTrapExpiredCertName OBJECT-TYPE
		SYNTAX		DisplayString(SIZE(0..64))
		MAX-ACCESS	accessible-for-notify
		STATUS		current
		DESCRIPTION
			"			
            This object is used in the traps to indicate the name of the certificate that has expired.
        			"
	::= {wlsxTrapObjectsGroup 135 }

	wlsxTrapHTMode OBJECT-TYPE
		SYNTAX		Integer32
		MAX-ACCESS	accessible-for-notify
		STATUS		current
		DESCRIPTION
			"			
                This object represents HT Mode.
            			"
	::= {wlsxTrapObjectsGroup 136 }

	wlsxTrapPhyType OBJECT-TYPE
		SYNTAX		Integer32
		MAX-ACCESS	accessible-for-notify
		STATUS		current
		DESCRIPTION
			"			
                This object represents Physical Type.
            			"
	::= {wlsxTrapObjectsGroup 137 }

	wlsxTrapAPManagedModeConfigFailure OBJECT-TYPE
		SYNTAX		DisplayString(SIZE(0..64))
		MAX-ACCESS	accessible-for-notify
		STATUS		current
		DESCRIPTION
			"			
            This object indicates the error for the failure of config apply on IAP.
        			"
	::= {wlsxTrapObjectsGroup 138 }

	wlsxTrapAuthServerAddress OBJECT-TYPE
		SYNTAX		IpAddress
		MAX-ACCESS	accessible-for-notify
		STATUS		current
		DESCRIPTION
			"			
            This object is used in the traps to indicate the
            Authentication Server IP used for Authentication.
        			"
	::= {wlsxTrapObjectsGroup 139 }

	wlsxTrapPortalServerName OBJECT-TYPE
		SYNTAX		DisplayString(SIZE(0..64))
		MAX-ACCESS	accessible-for-notify
		STATUS		current
		DESCRIPTION
			"			
            This object is used in the traps to indicate the
            Captive Portal Server used for Authentication.
        			"
	::= {wlsxTrapObjectsGroup 140 }

	wlsxTrapPortalServerAddress OBJECT-TYPE
		SYNTAX		DisplayString(SIZE(0..64))
		MAX-ACCESS	accessible-for-notify
		STATUS		current
		DESCRIPTION
			"			
            This object is used in the traps to indicate the
            Captive Portal Server IP or host name used for Authentication.
        			"
	::= {wlsxTrapObjectsGroup 141 }

	wlsxTrapPortalServerDownReason OBJECT-TYPE
		SYNTAX		ArubaPortalServerDownReason
		MAX-ACCESS	accessible-for-notify
		STATUS		current
		DESCRIPTION
			"			
            This object specifies the captive portal server down reason.
        			"
	::= {wlsxTrapObjectsGroup 142 }

	wlsxTrapLicensePlatformMismatchKey OBJECT-TYPE
		SYNTAX		DisplayString(SIZE(0..64))
		MAX-ACCESS	accessible-for-notify
		STATUS		current
		DESCRIPTION
			"			
            This object represents license incompatibility with the given
            platform.
        			"
	::= {wlsxTrapObjectsGroup 143 }

	wlsxTrapTargetAPName OBJECT-TYPE
		SYNTAX		DisplayString(SIZE(0..64))
		MAX-ACCESS	accessible-for-notify
		STATUS		current
		DESCRIPTION
			"			
              This object is used in the traps to indicate the target's AP name.
          			"
	::= {wlsxTrapObjectsGroup 144 }

	wlsxTrapTargetAPMac OBJECT-TYPE
		SYNTAX		MacAddress
		MAX-ACCESS	accessible-for-notify
		STATUS		current
		DESCRIPTION
			"			
              This object is used in the traps to indicate the target's MAC address.
          			"
	::= {wlsxTrapObjectsGroup 145 }

	wlsxTrapAPUSBStatus OBJECT-TYPE
		SYNTAX		DisplayString(SIZE(0..64))
		MAX-ACCESS	accessible-for-notify
		STATUS		current
		DESCRIPTION
			"			
            This object represents plug in or plug out status of an USB device.
        			"
	::= {wlsxTrapObjectsGroup 146 }

	wlsxTrapUSBVendorProductID OBJECT-TYPE
		SYNTAX		DisplayString(SIZE(0..64))
		MAX-ACCESS	accessible-for-notify
		STATUS		current
		DESCRIPTION
			"			
            This object represents vendor ID or product ID of an USB device.
        			"
	::= {wlsxTrapObjectsGroup 147 }

	wlsxTrapSwitchIpv6 OBJECT-TYPE
		SYNTAX		DisplayString(SIZE(0..64))
		MAX-ACCESS	accessible-for-notify
		STATUS		current
		DESCRIPTION
			"			
            This object represents the controller IPv6 address.
        			"
	::= {wlsxTrapObjectsGroup 148 }

	wlsxTrapStationBlackListReasonStr OBJECT-TYPE
		SYNTAX		DisplayString(SIZE(0..64))
		MAX-ACCESS	accessible-for-notify
		STATUS		obsolete
		DESCRIPTION
			"			
            The Reason for which a station is black listed in details.
            **NOTE: this trap is obsoleted and replaced by
            wlsxTrapStationDenyListReasonStr
        			"
	::= {wlsxTrapObjectsGroup 149 }

	wlsxTrapPeerIpAddress OBJECT-TYPE
		SYNTAX		DisplayString(SIZE(0..64))
		MAX-ACCESS	accessible-for-notify
		STATUS		current
		DESCRIPTION
			"			
              This object is used in the traps to indicate the peer IP address of Cluster VLAN probe.
          			"
	::= {wlsxTrapObjectsGroup 150 }

	wlsxTrapConnectionStatus OBJECT-TYPE
		SYNTAX		DisplayString(SIZE(0..64))
		MAX-ACCESS	accessible-for-notify
		STATUS		current
		DESCRIPTION
			"			
              This object is used in the traps to indicate the Connection status of Cluster VLAN probe.
          			"
	::= {wlsxTrapObjectsGroup 151 }

	wlsxTrapFailedVlan OBJECT-TYPE
		SYNTAX		Integer32
		MAX-ACCESS	accessible-for-notify
		STATUS		current
		DESCRIPTION
			"			
              This object is used in the traps to indicate the failed VLAN id of cluster VLAN probe.
          			"
	::= {wlsxTrapObjectsGroup 152 }

	wlsxTrapMatchedIpv6 OBJECT-TYPE
		SYNTAX		DisplayString(SIZE(0..64))
		MAX-ACCESS	accessible-for-notify
		STATUS		current
		DESCRIPTION
			"			
            This object is used in the traps to indicate the IPv6 address
        			"
	::= {wlsxTrapObjectsGroup 153 }

	wlsxTrapDeviceIpv6Address OBJECT-TYPE
		SYNTAX		DisplayString(SIZE(0..64))
		MAX-ACCESS	accessible-for-notify
		STATUS		current
		DESCRIPTION
			"			
            This object represents the IPv6 address of a device seen by an AP.
        			"
	::= {wlsxTrapObjectsGroup 154 }

	wlsxTrapAuthFailureReason OBJECT-TYPE
		SYNTAX		DisplayString(SIZE(0..64))
		MAX-ACCESS	accessible-for-notify
		STATUS		current
		DESCRIPTION
			"			
            This object represents the reason for the authentication failure.
        			"
	::= {wlsxTrapObjectsGroup 155 }

	wlsxTrapAPPhyType OBJECT-TYPE
		SYNTAX		ArubaPhyType
		MAX-ACCESS	accessible-for-notify
		STATUS		current
		DESCRIPTION
			"			
                This object represents Band Information.
            			"
	::= {wlsxTrapObjectsGroup 156 }

	wlsxTrapAPSecChannel OBJECT-TYPE
		SYNTAX		Integer32
		MAX-ACCESS	accessible-for-notify
		STATUS		current
		DESCRIPTION
			"			
                This object represents Secondary Channel.
            			"
	::= {wlsxTrapObjectsGroup 157 }

	wlsxTrapAPHTMode OBJECT-TYPE
		SYNTAX		ArubaHTMode
		MAX-ACCESS	accessible-for-notify
		STATUS		current
		DESCRIPTION
			"			
                This object represents HT-Mode Information.
            			"
	::= {wlsxTrapObjectsGroup 158 }

	wlsxTrapAPBand OBJECT-TYPE
		SYNTAX		DisplayString(SIZE(0..64))
		MAX-ACCESS	accessible-for-notify
		STATUS		current
		DESCRIPTION
			"			
            This object represents the radio band on which an AP operates on.
        			"
	::= {wlsxTrapObjectsGroup 159 }

	wlsxTrapTargetAPBand OBJECT-TYPE
		SYNTAX		DisplayString(SIZE(0..64))
		MAX-ACCESS	accessible-for-notify
		STATUS		current
		DESCRIPTION
			"			
            This object represents the radio band on which the target AP operates on.
        			"
	::= {wlsxTrapObjectsGroup 160 }

	wlsxTrapStationDenyListReason OBJECT-TYPE
		SYNTAX		ArubaDenyListReason
		MAX-ACCESS	accessible-for-notify
		STATUS		current
		DESCRIPTION
			"			
            The Reason for which a station is added to denylist.
        			"
	::= {wlsxTrapObjectsGroup 161 }

	wlsxTrapStationDenyListReasonStr OBJECT-TYPE
		SYNTAX		DisplayString(SIZE(0..64))
		MAX-ACCESS	accessible-for-notify
		STATUS		current
		DESCRIPTION
			"			
            The Reason for which a station is added to denylist in details.
        			"
	::= {wlsxTrapObjectsGroup 162 }

	wlsxTrapApConductorStatus OBJECT-TYPE
		SYNTAX		ArubaAPConductorStatus
		MAX-ACCESS	accessible-for-notify
		STATUS		current
		DESCRIPTION
			"			
            Status of the AP as seen by the conductor when the status changes.
        			"
	::= {wlsxTrapObjectsGroup 163 }

	wlsxTrapAPPrevPhyType OBJECT-TYPE
		SYNTAX		ArubaPhyType
		MAX-ACCESS	accessible-for-notify
		STATUS		current
		DESCRIPTION
			"			
            This object represents Prev Band Information.
        			"
	::= {wlsxTrapObjectsGroup 164 }

	wlsxTrapAPPrevHTMode OBJECT-TYPE
		SYNTAX		ArubaHTMode
		MAX-ACCESS	accessible-for-notify
		STATUS		current
		DESCRIPTION
			"			
            This object represents Previous HT-Mode Information.
        			"
	::= {wlsxTrapObjectsGroup 165 }

	wlsxLicenseType OBJECT-TYPE
		SYNTAX		DisplayString(SIZE(0..64))
		MAX-ACCESS	accessible-for-notify
		STATUS		current
		DESCRIPTION
			"			
          This object is used in the traps to indicate the License Type.
        			"
	::= {wlsxTrapObjectsGroup 166 }

	wlsxLicensePoolName OBJECT-TYPE
		SYNTAX		DisplayString(SIZE(0..64))
		MAX-ACCESS	accessible-for-notify
		STATUS		current
		DESCRIPTION
			"			
          This object is used in the traps to indicate the pool name for a License.
        			"
	::= {wlsxTrapObjectsGroup 167 }

-- Definition of traps

	wlsxVlanLinkUp NOTIFICATION-TYPE
		OBJECTS {wlsxTrapTime, wlsxTrapVlanId,wlsxTrapAdminStatus,
				wlsxTrapOperStatus}
		STATUS		current
		DESCRIPTION
			"			
            This trap indicates that a VLAN interface is up.
        	"
	::= {wlsxTrapDefinitionsGroup 1000 }

	wlsxVlanLinkDown NOTIFICATION-TYPE
		OBJECTS {wlsxTrapTime, wlsxTrapVlanId,wlsxTrapAdminStatus,
				wlsxTrapOperStatus}
		STATUS		current
		DESCRIPTION
			"			
            This trap indicates that a VLAN interface is down.
        	"
	::= {wlsxTrapDefinitionsGroup 1001 }

	wlsxSignatureMatch NOTIFICATION-TYPE
		OBJECTS {wlsxTrapTime, wlsxTrapSignatureName,wlsxTrapSourceMac,
				wlsxTrapSnr,wlsxTrapAPBSSID,
				wlsxTrapAPLocation}
		STATUS		current
		DESCRIPTION
			"			
            This trap indicates that a signature match was detected.
        	"
	::= {wlsxTrapDefinitionsGroup 1002 }

	wlsxNodeRateAnomaly NOTIFICATION-TYPE
		OBJECTS {wlsxTrapTime, wlsxTrapFrameType,wlsxTrapNodeMac,
				wlsxTrapSnr,wlsxTrapAPBSSID,
				wlsxTrapAPLocation}
		STATUS		current
		DESCRIPTION
			"			
            This trap indicates that a node is exceeding the threshold set for 
            the frame type.
        	"
	::= {wlsxTrapDefinitionsGroup 1003 }

	wlsxNormalTemperature NOTIFICATION-TYPE
		OBJECTS {wlsxTrapTime, wlsxTrapTemperatureValue}
		STATUS		current
		DESCRIPTION
			"			
            This trap indicates that the Temperature has returned to 
            an acceptable range.
        	"
	::= {wlsxTrapDefinitionsGroup 1004 }

	wlsxProcessRestart NOTIFICATION-TYPE
		OBJECTS {wlsxTrapTime, wlsxTrapProcessName}
		STATUS		current
		DESCRIPTION
			"			
            This trap indicates that the named process has been restarted.
        	"
	::= {wlsxTrapDefinitionsGroup 1005 }

	wlsxFlashSpaceOK NOTIFICATION-TYPE
		OBJECTS {wlsxTrapTime}
		STATUS		current
		DESCRIPTION
			"			
            This trap which indicates that the system flash space is back 
            to a sufficient level.
        	"
	::= {wlsxTrapDefinitionsGroup 1006 }

	wlsxMemoryUsageOK NOTIFICATION-TYPE
		OBJECTS {wlsxTrapTime}
		STATUS		current
		DESCRIPTION
			"			
            This trap which indicates that the free memory usage is back 
            to a sufficient level.
        	"
	::= {wlsxTrapDefinitionsGroup 1007 }

	wlsxPowerSupplyOK NOTIFICATION-TYPE
		OBJECTS {wlsxTrapTime}
		STATUS		current
		DESCRIPTION
			"			
            This trap indicates that the system power supply condition have
            returned to normal operation status.
        	"
	::= {wlsxTrapDefinitionsGroup 1008 }

	wlsxFanOK NOTIFICATION-TYPE
		OBJECTS {wlsxTrapTime, wlsxTrapFanNumber}
		STATUS		current
		DESCRIPTION
			"			
            This trap indicates that the fan has returned to normal.
        	"
	::= {wlsxTrapDefinitionsGroup 1009 }

	wlsxInRangeVoltage NOTIFICATION-TYPE
		OBJECTS {wlsxTrapTime, wlsxTrapVoltageType,wlsxTrapVoltageValue}
		STATUS		current
		DESCRIPTION
			"			
            This trap indicates that the controller Voltage is back within range.
        	"
	::= {wlsxTrapDefinitionsGroup 1010 }

	wlsxCoverageHoleResolved NOTIFICATION-TYPE
		OBJECTS {wlsxTrapTime, wlsxTrapAPBSSID,wlsxTrapAPLocation,
				wlsxTrapAPIpAddress,wlsxTrapNodeMac}
		STATUS		current
		DESCRIPTION
			"			
            This trap indicates that a coverage hole at location 
            wlsxTrapAPLocation has been resolved.
        	"
	::= {wlsxTrapDefinitionsGroup 1011 }

	wlsxNSwitchIPChanged NOTIFICATION-TYPE
		OBJECTS {wlsxTrapTime, wlsxTrapSwitchIp}
		STATUS		current
		DESCRIPTION
			"			
            This trap indicates that the controller IP address has changed.
        	"
	::= {wlsxTrapDefinitionsGroup 1012 }

	wlsxNSwitchRoleChange NOTIFICATION-TYPE
		OBJECTS {wlsxTrapTime, wlsxTrapSwitchRole}
		STATUS		current
		DESCRIPTION
			"			
            This trap indicates that the role of the controller IP address has 
            changed.
        	"
	::= {wlsxTrapDefinitionsGroup 1013 }

	wlsxNUserEntryCreated NOTIFICATION-TYPE
		OBJECTS {wlsxTrapTime, wlsxTrapUserIpAddress,wlsxTrapUserPhyAddress}
		STATUS		current
		DESCRIPTION
			"			
            This trap indicates that a new user was created.
        	"
	::= {wlsxTrapDefinitionsGroup 1014 }

	wlsxNUserEntryDeleted NOTIFICATION-TYPE
		OBJECTS {wlsxTrapTime, wlsxTrapUserIpAddress,wlsxTrapUserPhyAddress}
		STATUS		current
		DESCRIPTION
			"			
            This trap indicates that a user was deleted.
        	"
	::= {wlsxTrapDefinitionsGroup 1015 }

	wlsxNUserEntryAuthenticated NOTIFICATION-TYPE
		OBJECTS {wlsxTrapTime, wlsxTrapUserIpAddress,wlsxTrapUserPhyAddress,
				wlsxTrapUserName,wlsxTrapUserAuthenticationMethod,
				wlsxTrapUserRole}
		STATUS		current
		DESCRIPTION
			"			
            This trap indicates that a user is Authenticated.
        	"
	::= {wlsxTrapDefinitionsGroup 1016 }

	wlsxNUserEntryDeAuthenticated NOTIFICATION-TYPE
		OBJECTS {wlsxTrapTime, wlsxTrapUserIpAddress,wlsxTrapUserPhyAddress}
		STATUS		current
		DESCRIPTION
			"			
            This trap indicates that a user is Deauthenticated.
        	"
	::= {wlsxTrapDefinitionsGroup 1017 }

	wlsxNUserAuthenticationFailed NOTIFICATION-TYPE
		OBJECTS {wlsxTrapTime, wlsxTrapUserName,wlsxTrapUserIpAddress,
				wlsxTrapUserPhyAddress,wlsxTrapAuthServerName,
				wlsxTrapAuthServerAddress,wlsxTrapAPBSSID,
				wlsxTrapAPName}
		STATUS		current
		DESCRIPTION
			"			
            This trap indicates that a user authentication has failed.
        	"
	::= {wlsxTrapDefinitionsGroup 1018 }

	wlsxNAuthServerReqTimedOut NOTIFICATION-TYPE
		OBJECTS {wlsxTrapTime, wlsxTrapUserName,wlsxTrapUserIpAddress,
				wlsxTrapUserPhyAddress,wlsxTrapAuthServerName,
				wlsxTrapAuthServerAddress,wlsxTrapAPBSSID,
				wlsxTrapAPName}
		STATUS		current
		DESCRIPTION
			"			
            This trap indicates that the authentication server request timed out.
        	"
	::= {wlsxTrapDefinitionsGroup 1019 }

	wlsxNAuthServerTimedOut NOTIFICATION-TYPE
		OBJECTS {wlsxTrapTime, wlsxTrapAuthServerName,wlsxTrapAuthServerAddress,
				wlsxTrapAuthServerTimeout,wlsxTrapUserName,
				wlsxTrapUserIpAddress,wlsxTrapUserPhyAddress,
				wlsxTrapAPBSSID,wlsxTrapAPName}
		STATUS		current
		DESCRIPTION
			"			
            This trap indicates that the authentication server timed out.
        	"
	::= {wlsxTrapDefinitionsGroup 1020 }

	wlsxNAuthServerIsUp NOTIFICATION-TYPE
		OBJECTS {wlsxTrapTime, wlsxTrapAuthServerName,wlsxTrapAuthServerAddress}
		STATUS		current
		DESCRIPTION
			"			
            This trap indicates that an authentication server is up.
        	"
	::= {wlsxTrapDefinitionsGroup 1021 }

	wlsxNAuthMaxUserEntries NOTIFICATION-TYPE
		OBJECTS {wlsxTrapTime}
		STATUS		current
		DESCRIPTION
			"			
            A trap which indicates that the user entries table is full and 
            cannot add any more entries.
        	"
	::= {wlsxTrapDefinitionsGroup 1022 }

	wlsxNAuthMaxAclEntries NOTIFICATION-TYPE
		OBJECTS {wlsxTrapTime}
		STATUS		current
		DESCRIPTION
			"			
            A trap which indicates that the ACL Entries table is full and 
            cannot add any more entries.
        	"
	::= {wlsxTrapDefinitionsGroup 1023 }

	wlsxNAuthMaxBWContracts NOTIFICATION-TYPE
		OBJECTS {wlsxTrapTime}
		STATUS		current
		DESCRIPTION
			"			
            A trap which indicates that the controller reached the maximum number 
            of configurable Bandwidth contracts. 
        	"
	::= {wlsxTrapDefinitionsGroup 1024 }

	wlsxNPowerSupplyFailure NOTIFICATION-TYPE
		OBJECTS {wlsxTrapTime}
		STATUS		current
		DESCRIPTION
			"			
            A trap which indicates that the power supply has failed.
        	"
	::= {wlsxTrapDefinitionsGroup 1025 }

	wlsxNFanFailure NOTIFICATION-TYPE
		OBJECTS {wlsxTrapTime, wlsxTrapFanNumber}
		STATUS		current
		DESCRIPTION
			"			
            A trap which indicates that the fan has failed.
        	"
	::= {wlsxTrapDefinitionsGroup 1026 }

	wlsxNOutOfRangeVoltage NOTIFICATION-TYPE
		OBJECTS {wlsxTrapTime, wlsxTrapVoltageType,wlsxTrapVoltageValue}
		STATUS		current
		DESCRIPTION
			"			
            A trap which indicates that the controller voltage is out of range.
        	"
	::= {wlsxTrapDefinitionsGroup 1027 }

	wlsxNOutOfRangeTemperature NOTIFICATION-TYPE
		OBJECTS {wlsxTrapTime, wlsxTrapTemperatureValue}
		STATUS		current
		DESCRIPTION
			"			
            A trap which indicates that the controller internal temperature is
            out of range. 
        	"
	::= {wlsxTrapDefinitionsGroup 1028 }

	wlsxNLCInserted NOTIFICATION-TYPE
		OBJECTS {wlsxTrapTime, wlsxTrapCardSlot}
		STATUS		current
		DESCRIPTION
			"			
            A Trap which indicates that a line card is inserted.
        	"
	::= {wlsxTrapDefinitionsGroup 1029 }

	wlsxNSCInserted NOTIFICATION-TYPE
		OBJECTS {wlsxTrapTime, wlsxTrapCardSlot}
		STATUS		current
		DESCRIPTION
			"			
            a Trap which indicates that a supervisor card is inserted.
        	"
	::= {wlsxTrapDefinitionsGroup 1030 }

	wlsxNGBICInserted NOTIFICATION-TYPE
		OBJECTS {wlsxTrapTime}
		STATUS		current
		DESCRIPTION
			"			
            A Trap which indicates that a GBIC is inserted in a Line Card.
        	"
	::= {wlsxTrapDefinitionsGroup 1031 }

	wlsxNProcessDied NOTIFICATION-TYPE
		OBJECTS {wlsxTrapTime, wlsxTrapProcessName}
		STATUS		current
		DESCRIPTION
			"			
            A Trap which indicates that a process has died.
        	"
	::= {wlsxTrapDefinitionsGroup 1032 }

	wlsxNProcessExceedsMemoryLimits NOTIFICATION-TYPE
		OBJECTS {wlsxTrapTime, wlsxTrapProcessName}
		STATUS		current
		DESCRIPTION
			"			
            A Trap which indicates that a process is consuming Large
            amounts of memory.
        	"
	::= {wlsxTrapDefinitionsGroup 1033 }

	wlsxNLowOnFlashSpace NOTIFICATION-TYPE
		OBJECTS {wlsxTrapTime}
		STATUS		current
		DESCRIPTION
			"			
            A Trap which indicates that the controller is running low on flash space.
        	"
	::= {wlsxTrapDefinitionsGroup 1034 }

	wlsxNLowMemory NOTIFICATION-TYPE
		OBJECTS {wlsxTrapTime}
		STATUS		current
		DESCRIPTION
			"			
            A Trap which indicates that the system free memory is low.
        	"
	::= {wlsxTrapDefinitionsGroup 1035 }

	wlsxNFanTrayRemoved NOTIFICATION-TYPE
		OBJECTS {wlsxTrapTime}
		STATUS		current
		DESCRIPTION
			"			
            A Trap which indicates that a fan tray is removed.
        	"
	::= {wlsxTrapDefinitionsGroup 1036 }

	wlsxNFanTrayInserted NOTIFICATION-TYPE
		OBJECTS {wlsxTrapTime}
		STATUS		current
		DESCRIPTION
			"			
            A Trap which indicates that a fan tray is inserted.
        	"
	::= {wlsxTrapDefinitionsGroup 1037 }

	wlsxNLCRemoved NOTIFICATION-TYPE
		OBJECTS {wlsxTrapTime, wlsxTrapCardSlot}
		STATUS		current
		DESCRIPTION
			"			
            A Trap which indicates that a Line card is removed.
        	"
	::= {wlsxTrapDefinitionsGroup 1038 }

	wlsxNPowerSupplyMissing NOTIFICATION-TYPE
		OBJECTS {wlsxTrapTime}
		STATUS		current
		DESCRIPTION
			"			
            A Trap which indicates that the power supply is missing.
        	"
	::= {wlsxTrapDefinitionsGroup 1039 }

	wlsxNAccessPointIsUp NOTIFICATION-TYPE
		OBJECTS {wlsxTrapTime, wlsxTrapAPMacAddress}
		STATUS		current
		DESCRIPTION
			"			
            A Trap which indicates that an access point up.
        	"
	::= {wlsxTrapDefinitionsGroup 1040 }

	wlsxNAccessPointIsDown NOTIFICATION-TYPE
		OBJECTS {wlsxTrapTime, wlsxTrapAPMacAddress}
		STATUS		current
		DESCRIPTION
			"			
            A Trap which indicates that an access point down.
        	"
	::= {wlsxTrapDefinitionsGroup 1041 }

	wlsxNCoverageHoleDetected NOTIFICATION-TYPE
		OBJECTS {wlsxTrapTime, wlsxTrapAPBSSID,wlsxTrapAPLocation,
				wlsxTrapAPIpAddress,wlsxTrapNodeMac}
		STATUS		current
		DESCRIPTION
			"			
            This trap indicates that an access point at Location 
            wlsxTrapAPLocation has detected a Coverage Hole.
        	"
	::= {wlsxTrapDefinitionsGroup 1042 }

	wlsxNChannelChanged NOTIFICATION-TYPE
		OBJECTS {wlsxTrapTime, wlsxTrapAPBSSID,wlsxTrapAPLocation,
				wlsxTrapAPChannel}
		STATUS		current
		DESCRIPTION
			"			
            This trap indicates that an access point at Location 
            wlsxTrapAPLocation has changed the channel.
        	"
	::= {wlsxTrapDefinitionsGroup 1043 }

	wlsxNStationAddedToBlackList NOTIFICATION-TYPE
		OBJECTS {wlsxTrapTime, wlsxTrapNodeMac,wlsxTrapStationBlackListReason,
				wlsxTrapStationBlackListReasonStr}
		STATUS		obsolete
		DESCRIPTION
			"			
            This trap indicates that the station is black listed. 
            **NOTE: this trap is obsoleted and replaced by
            wlsxNStationAddedToDenyList
        	"
	::= {wlsxTrapDefinitionsGroup 1044 }

	wlsxNStationRemovedFromBlackList NOTIFICATION-TYPE
		OBJECTS {wlsxTrapTime, wlsxTrapNodeMac}
		STATUS		obsolete
		DESCRIPTION
			"			
            This trap indicates that the station is removed from the black list. 
            **NOTE: this trap is obsoleted and replaced by
            wlsxNStationRemovedFromDenyList
        	"
	::= {wlsxTrapDefinitionsGroup 1045 }

	wlsxNIpSpoofingDetected NOTIFICATION-TYPE
		OBJECTS {wlsxTrapTime, wlsxTrapSpoofedIpAddress,wlsxTrapSpoofedOldPhyAddress,
				wlsxTrapSpoofedNewPhyAddress}
		STATUS		current
		DESCRIPTION
			"			
            A trap indicating that the controller detected IP Spoofing. 
        	"
	::= {wlsxTrapDefinitionsGroup 1046 }

	wlsxNDBCommunicationFailure NOTIFICATION-TYPE
		OBJECTS {wlsxTrapTime, wlsxTrapDBName,wlsxTrapDBUserName,
				wlsxTrapDBIpAddress,wlsxTrapDBType}
		STATUS		current
		DESCRIPTION
			"			
            This trap indicates that communication with Database failed. 
        	"
	::= {wlsxTrapDefinitionsGroup 1047 }

	wlsxNVrrpStateChange NOTIFICATION-TYPE
		OBJECTS {wlsxTrapTime, wlsxTrapVrrpID,wlsxTrapVrrpMasterIp,
				wlsxTrapVrrpOperState}
		STATUS		current
		DESCRIPTION
			"			
            This trap indicates that VRRP state has changed on the controller. 
        	"
	::= {wlsxTrapDefinitionsGroup 1048 }

	wlsxNRadioAttributesChanged NOTIFICATION-TYPE
		OBJECTS {wlsxTrapTime, wlsxTrapAPMacAddress,wlsxTrapAPRadioNumber,
				wlsxTrapAPIpAddress,wlsxTrapAPChannel,
				wlsxTrapAPTxPower,wlsxTrapAPSecChannel,
				wlsxTrapAPPhyType,wlsxTrapAPHTMode}
		STATUS		current
		DESCRIPTION
			"			
            A Trap which indicates changes in the Radio attributes of an 
            access point.
        	"
	::= {wlsxTrapDefinitionsGroup 1049 }

	wlsxNESIServerUp NOTIFICATION-TYPE
		OBJECTS {wlsxTrapTime, wlsxTrapESIServerGrpName,wlsxTrapESIServerName,
				wlsxTrapESIServerIpAddress}
		STATUS		current
		DESCRIPTION
			"			
            A Trap which indicates that a ESI server is up.
        	"
	::= {wlsxTrapDefinitionsGroup 1050 }

	wlsxNESIServerDown NOTIFICATION-TYPE
		OBJECTS {wlsxTrapTime, wlsxTrapESIServerGrpName,wlsxTrapESIServerName,
				wlsxTrapESIServerIpAddress}
		STATUS		current
		DESCRIPTION
			"			
            A Trap which indicates that a ESI server is down.
        	"
	::= {wlsxTrapDefinitionsGroup 1051 }

	wlsxNLicenseExpiry NOTIFICATION-TYPE
		OBJECTS {wlsxTrapTime, wlsxTrapLicenseDaysRemaining}
		STATUS		current
		DESCRIPTION
			"			
            A Trap which indicates that one or more licenses on the controller will expire in wlsxTrapLicenseDaysRemaining days.
        	"
	::= {wlsxTrapDefinitionsGroup 1052 }

	wlsxUnsecureAPDetected NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapMatchedMac,wlsxTrapMatchedIp,
				wlsxTrapRogueInfoURL,wlsxTrapMatchedIpv6,
				wlsxTrapAPBand}
		STATUS		current
		DESCRIPTION
			"			This trap indicates that an unauthorized access point is connected to the wired network. The access point is declared Rogue because it was matched to a MAC address.  	"
	::= {wlsxTrapDefinitionsGroup 1053 }

	wlsxUnsecureAPResolved NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
                This trap indicates that a previously detected access point, classified as Rogue,
                is no longer present in the network.
			"
	::= {wlsxTrapDefinitionsGroup 1054 }

	wlsxStaImpersonation NOTIFICATION-TYPE
		OBJECTS {wlsxTrapTime, wlsxTrapNodeMac,wlsxTrapAPMacAddress,
				wlsxTrapAPRadioNumber,wlsxTrapAPLocation}
		STATUS		current
		DESCRIPTION
			"			
			This trap indicates that an AM detected Station Impersonation.
			"
	::= {wlsxTrapDefinitionsGroup 1055 }

	wlsxReservedChannelViolation NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
				This trap indicates that an AM detected an access point
				which is violating the Reserved Channel configuration.
			"
	::= {wlsxTrapDefinitionsGroup 1056 }

	wlsxValidSSIDViolation NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP has detected an access point is violating 
            Valid SSID configuration by using an SSID that is reserved for use by a valid AP only. 
			"
	::= {wlsxTrapDefinitionsGroup 1057 }

	wlsxChannelMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected an access point that has a channel misconfiguration 
            because it is using a channel that is not valid.   
			"
	::= {wlsxTrapDefinitionsGroup 1058 }

	wlsxOUIMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected an access point that has an OUI misconfiguration because
            it is using an OUI that is not valid.
			"
	::= {wlsxTrapDefinitionsGroup 1059 }

	wlsxSSIDMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected an access point that has an SSID misconfiguration because it is using
            an SSID that is not valid.
			"
	::= {wlsxTrapDefinitionsGroup 1060 }

	wlsxShortPreableMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that an access point has bad Short preamble
			configuration.
			"
	::= {wlsxTrapDefinitionsGroup 1061 }

	wlsxWPAMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected an access point that is misconfigured because it is not using WPA.
			"
	::= {wlsxTrapDefinitionsGroup 1062 }

	wlsxAdhocNetworkDetected NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that an AM has detected an Ad hoc
			network.
			"
	::= {wlsxTrapDefinitionsGroup 1063 }

	wlsxAdhocNetworkRemoved NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that a previously detected Ad hoc Network is no
            longer present in the network.
			"
	::= {wlsxTrapDefinitionsGroup 1064 }

	wlsxStaPolicyViolation NOTIFICATION-TYPE
		OBJECTS {wlsxTrapTime, wlsxTrapTargetAPBSSID,wlsxTrapNodeMac,
				wlsxTrapAPMacAddress,wlsxTrapAPRadioNumber,
				wlsxTrapAPLocation,wlsxTrapAPChannel,
				wlsxTrapAPBand}
		STATUS		current
		DESCRIPTION
			"			
			This trap indicates that Protection was enforced because a valid station's association to a non-valid access point violated Valid Station policy.
			"
	::= {wlsxTrapDefinitionsGroup 1065 }

	wlsxRepeatWEPIVViolation NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
		    This trap indicates that an AP detected that a valid access point is using the same WEP initialization vector in consecutive packets.
			"
	::= {wlsxTrapDefinitionsGroup 1066 }

	wlsxWeakWEPIVViolation NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected that a valid access point is using a Weak WEP initialization vector.
			"
	::= {wlsxTrapDefinitionsGroup 1067 }

	wlsxChannelInterferenceDetected NOTIFICATION-TYPE
		OBJECTS {wlsxTrapTime, wlsxTrapAPMacAddress,wlsxTrapAPRadioNumber,
				wlsxTrapAPLocation,wlsxTrapAPChannel}
		STATUS		current
		DESCRIPTION
			"			
			This trap indicates that an AP has detected channel interference.
			"
	::= {wlsxTrapDefinitionsGroup 1068 }

	wlsxChannelInterferenceCleared NOTIFICATION-TYPE
		OBJECTS {wlsxTrapTime, wlsxTrapAPMacAddress,wlsxTrapAPRadioNumber,
				wlsxTrapAPLocation,wlsxTrapAPChannel}
		STATUS		current
		DESCRIPTION
			"			
			This trap indicates that a previously detected channel interference
            is no longer present. 
			"
	::= {wlsxTrapDefinitionsGroup 1069 }

	wlsxAPInterferenceDetected NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP has detected interference for an access point.
			"
	::= {wlsxTrapDefinitionsGroup 1070 }

	wlsxAPInterferenceCleared NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that the previously detected interference for an access point
            is no longer present. 
			"
	::= {wlsxTrapDefinitionsGroup 1071 }

	wlsxStaInterferenceDetected NOTIFICATION-TYPE
		OBJECTS {wlsxTrapTime, wlsxTrapTargetAPBSSID,wlsxTrapTargetAPSSID,
				wlsxTrapAPMacAddress,wlsxTrapAPRadioNumber,
				wlsxTrapNodeMac,wlsxTrapAPLocation,
				wlsxTrapAPChannel,wlsxTrapAPBand}
		STATUS		current
		DESCRIPTION
			"			
			This trap indicates that an AP has detected interference for a station.
			"
	::= {wlsxTrapDefinitionsGroup 1072 }

	wlsxStaInterferenceCleared NOTIFICATION-TYPE
		OBJECTS {wlsxTrapTime, wlsxTrapTargetAPBSSID,wlsxTrapTargetAPSSID,
				wlsxTrapAPMacAddress,wlsxTrapAPRadioNumber,
				wlsxTrapNodeMac,wlsxTrapAPLocation,
				wlsxTrapAPChannel,wlsxTrapAPBand}
		STATUS		current
		DESCRIPTION
			"			
			This trap indicates that the previously detected interference for a station
            is no longer present. 
			"
	::= {wlsxTrapDefinitionsGroup 1073 }

	wlsxFrameRetryRateExceeded NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected that an access point has exceeded the configured upper threshold for Frame Retry Rate.
			"
	::= {wlsxTrapDefinitionsGroup 1074 }

	wlsxFrameReceiveErrorRateExceeded NOTIFICATION-TYPE
		OBJECTS {wlsxTrapTime, wlsxTrapTargetAPBSSID,wlsxTrapTargetAPSSID,
				wlsxTrapAPMacAddress,wlsxTrapAPRadioNumber,
				wlsxTrapTargetAPChannel,wlsxTrapAPLocation,
				wlsxTrapAPBand}
		STATUS		current
		DESCRIPTION
			"			
			This trap indicates that an AP detected that an access point has exceeded the configured upper threshold for Frame Receive Error Rate.
			"
	::= {wlsxTrapDefinitionsGroup 1075 }

	wlsxFrameFragmentationRateExceeded NOTIFICATION-TYPE
		OBJECTS {wlsxTrapTime, wlsxTrapTargetAPBSSID,wlsxTrapTargetAPSSID,
				wlsxTrapAPMacAddress,wlsxTrapAPRadioNumber,
				wlsxTrapTargetAPChannel,wlsxTrapAPLocation,
				wlsxTrapAPBand}
		STATUS		current
		DESCRIPTION
			"			
			This trap indicates that an AP detected that an access point exceeded the configured upper threshold for Frame Fragmentation Rate.
			"
	::= {wlsxTrapDefinitionsGroup 1076 }

	wlsxFrameBandWidthRateExceeded NOTIFICATION-TYPE
		OBJECTS {wlsxTrapTime, wlsxTrapNodeMac,wlsxTrapTargetAPBSSID,
				wlsxTrapTargetAPSSID,wlsxTrapAPMacAddress,
				wlsxTrapAPRadioNumber,wlsxTrapAPLocation,
				wlsxTrapAPChannel,wlsxTrapAPBand}
		STATUS		current
		DESCRIPTION
			"			
			This trap indicates that an AP detected that a station or access point has exceeded the configured upper threshold for Bandwidth rate. 
			"
	::= {wlsxTrapDefinitionsGroup 1077 }

	wlsxFrameLowSpeedRateExceeded NOTIFICATION-TYPE
		OBJECTS {wlsxTrapTime, wlsxTrapNodeMac,wlsxTrapTargetAPBSSID,
				wlsxTrapTargetAPSSID,wlsxTrapAPMacAddress,
				wlsxTrapAPRadioNumber,wlsxTrapAPLocation,
				wlsxTrapAPChannel,wlsxTrapAPBand}
		STATUS		current
		DESCRIPTION
			"			
			This trap indicates that an AP detected that a station has exceeded the configured upper threshold for Low speed rate. 
			"
	::= {wlsxTrapDefinitionsGroup 1078 }

	wlsxFrameNonUnicastRateExceeded NOTIFICATION-TYPE
		OBJECTS {wlsxTrapTime, wlsxTrapNodeMac,wlsxTrapTargetAPBSSID,
				wlsxTrapTargetAPSSID,wlsxTrapAPMacAddress,
				wlsxTrapAPRadioNumber,wlsxTrapAPLocation,
				wlsxTrapAPChannel,wlsxTrapAPBand}
		STATUS		current
		DESCRIPTION
			"			
			This trap indicates that an AP detected that a station has exceeded the configured upper threshold for Non Unicast traffic rate. 
			"
	::= {wlsxTrapDefinitionsGroup 1079 }

	wlsxLoadbalancingEnabled NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that an AM is reporting that an AP 
			has enabled Load balancing.
			"
	::= {wlsxTrapDefinitionsGroup 1080 }

	wlsxLoadbalancingDisabled NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that an AM is reporting that an AP
			has enabled Load balancing.
			"
	::= {wlsxTrapDefinitionsGroup 1081 }

	wlsxChannelFrameRetryRateExceeded NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that an AP has detected that the configured upper threshold for Frame Retry Rate was exceeded on a channel. 
			"
	::= {wlsxTrapDefinitionsGroup 1082 }

	wlsxChannelFrameFragmentationRateExceeded NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that an AP has detected that the configured upper threshold for Frame Fragmentation Rate was exceeded on a channel. 
			"
	::= {wlsxTrapDefinitionsGroup 1083 }

	wlsxChannelFrameErrorRateExceeded NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that an AP has detected that the configured upper threshold for Frame Receive Error Rate was exceeded on a channel. 
			"
	::= {wlsxTrapDefinitionsGroup 1084 }

	wlsxSignatureMatchAP NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match in a frame from an access point.
			"
	::= {wlsxTrapDefinitionsGroup 1085 }

	wlsxSignatureMatchSta NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match in a frame from a Station.
			"
	::= {wlsxTrapDefinitionsGroup 1086 }

	wlsxChannelRateAnomaly NOTIFICATION-TYPE
		OBJECTS {wlsxTrapTime, wlsxTrapFrameType,wlsxTrapAPMacAddress,
				wlsxTrapAPRadioNumber,wlsxTrapAPLocation,
				wlsxTrapAPChannel,wlsxTrapAPBand}
		STATUS		current
		DESCRIPTION
			"			
			This trap indicates that an AP detected frames on a channel which 
            exceed the configured IDS rate threshold.
			"
	::= {wlsxTrapDefinitionsGroup 1087 }

	wlsxNodeRateAnomalyAP NOTIFICATION-TYPE
		OBJECTS {wlsxTrapTime, wlsxTrapFrameType,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected frames transmitted or received by an 
            access point, which exceed the configured IDS rate threshold.
			"
	::= {wlsxTrapDefinitionsGroup 1088 }

	wlsxNodeRateAnomalySta NOTIFICATION-TYPE
		OBJECTS {wlsxTrapTime, wlsxTrapFrameType,wlsxTrapNodeMac,
				wlsxTrapSnr,wlsxTrapAPMacAddress,
				wlsxTrapAPRadioNumber,wlsxTrapAPLocation}
		STATUS		current
		DESCRIPTION
			"			
			This trap indicates that an AP detected frames transmitted or received by a 
            node, which exceed the configured IDS rate threshold.
			"
	::= {wlsxTrapDefinitionsGroup 1089 }

	wlsxEAPRateAnomaly NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that the rate of EAP Handshake packets 
            received by an AP has exceeded the configured IDS EAP Handshake rate threshold.
			"
	::= {wlsxTrapDefinitionsGroup 1090 }

	wlsxSignalAnomaly NOTIFICATION-TYPE
		OBJECTS {wlsxTrapTime, wlsxTrapAPMacAddress,wlsxTrapAPRadioNumber,
				wlsxTrapAPLocation,wlsxTrapAPChannel}
		STATUS		current
		DESCRIPTION
			"			
		    This trap indicates that an AM detected a Signal Anomaly.
			"
	::= {wlsxTrapDefinitionsGroup 1091 }

	wlsxSequenceNumberAnomalyAP NOTIFICATION-TYPE
		OBJECTS {wlsxTrapTime, wlsxTrapTargetAPBSSID,wlsxTrapTargetAPSSID,
				wlsxTrapSnr,wlsxTrapAPMacAddress,
				wlsxTrapAPRadioNumber,wlsxTrapAPLocation}
		STATUS		current
		DESCRIPTION
			"			
			This trap indicates that an AM received packets from an AP
			which exceeds the acceptable sequence number difference. 
            The acceptable sequence number difference is an IDS configuration 
            object.
			"
	::= {wlsxTrapDefinitionsGroup 1092 }

	wlsxSequenceNumberAnomalySta NOTIFICATION-TYPE
		OBJECTS {wlsxTrapTime, wlsxTrapSourceMac,wlsxTrapSnr,
				wlsxTrapAPMacAddress,wlsxTrapAPRadioNumber,
				wlsxTrapAPLocation}
		STATUS		current
		DESCRIPTION
			"			
			This trap indicates that an AM received packets from a Node
			which exceeds the acceptable sequence number difference. 
            The acceptable sequence number difference is an IDS configuration 
            object.
                	"
	::= {wlsxTrapDefinitionsGroup 1093 }

	wlsxDisconnectStationAttack NOTIFICATION-TYPE
		OBJECTS {wlsxTrapTime, wlsxTrapFrameType,wlsxTrapSourceMac,
				wlsxTrapSnr,wlsxTrapAPMacAddress,
				wlsxTrapAPRadioNumber,wlsxTrapAPLocation}
		STATUS		current
		DESCRIPTION
			"			
			This trap indicates that an AM detected a station Disconnect 
            attack.
			"
	::= {wlsxTrapDefinitionsGroup 1094 }

	wlsxApFloodAttack NOTIFICATION-TYPE
		OBJECTS {wlsxTrapTime, wlsxTrapAPMacAddress,wlsxTrapAPRadioNumber,
				wlsxTrapAPLocation}
		STATUS		current
		DESCRIPTION
			"			
			This trap indicates that the number of potential fake APs detected by 
			an AP has exceeded the configured IDS threshold. This is the total number of fake APs observed across all bands.
			"
	::= {wlsxTrapDefinitionsGroup 1095 }

	wlsxAdhocNetwork NOTIFICATION-TYPE
		OBJECTS {wlsxTrapTime, wlsxTrapSourceMac,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AM detected an Ad hoc 
			Network. An Station is connected to an ad hoc AP.
			"
	::= {wlsxTrapDefinitionsGroup 1096 }

	wlsxWirelessBridge NOTIFICATION-TYPE
		OBJECTS {wlsxTrapTime, wlsxTrapTransmitterMac,wlsxTrapReceiverMac,
				wlsxTrapSnr,wlsxTrapAPMacAddress,
				wlsxTrapAPRadioNumber,wlsxTrapAPLocation}
		STATUS		current
		DESCRIPTION
			"			
			This trap indicates that an AP detected a Wireless Bridge when a WDS frame was seen between the transmitter and receiver addresses.
			"
	::= {wlsxTrapDefinitionsGroup 1097 }

	wlsxInvalidMacOUIAP NOTIFICATION-TYPE
		OBJECTS {wlsxTrapTime, wlsxTrapAddressType,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected an invalid MAC OUI in the BSSID of a frame.  An invalid MAC OUI suggests that the frame may be spoofed.
			"
	::= {wlsxTrapDefinitionsGroup 1098 }

	wlsxInvalidMacOUISta NOTIFICATION-TYPE
		OBJECTS {wlsxTrapTime, wlsxTrapAddressType,wlsxTrapNodeMac,
				wlsxTrapSnr,wlsxTrapAPMacAddress,
				wlsxTrapAPRadioNumber,wlsxTrapAPLocation}
		STATUS		current
		DESCRIPTION
			"			
			This trap indicates that an AP detected an invalid MAC OUI in the SRC or DST address of a frame. An invalid MAC OUI suggests that the frame may be spoofed.
			"
	::= {wlsxTrapDefinitionsGroup 1099 }

	wlsxWEPMisconfiguration NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected an access point that is misconfigured because it does not have Privacy enabled.
			"
	::= {wlsxTrapDefinitionsGroup 1100 }

	wlsxStaRepeatWEPIVViolation NOTIFICATION-TYPE
		OBJECTS {wlsxTrapTime, wlsxTrapTargetAPBSSID,wlsxTrapTargetAPSSID,
				wlsxTrapNodeMac,wlsxTrapAPMacAddress,
				wlsxTrapAPRadioNumber,wlsxTrapAPLocation,
				wlsxTrapAPChannel,wlsxTrapAPBand}
		STATUS		current
		DESCRIPTION
			"			
			This trap indicates that an AP detected that a valid station is using the same WEP initialization vector in consecutive packets.
			"
	::= {wlsxTrapDefinitionsGroup 1101 }

	wlsxStaWeakWEPIVViolation NOTIFICATION-TYPE
		OBJECTS {wlsxTrapTime, wlsxTrapTargetAPBSSID,wlsxTrapTargetAPSSID,
				wlsxTrapNodeMac,wlsxTrapAPMacAddress,
				wlsxTrapAPRadioNumber,wlsxTrapAPLocation,
				wlsxTrapAPChannel,wlsxTrapAPBand}
		STATUS		current
		DESCRIPTION
			"			
			This trap indicates that an AP detected that a valid station is using a Weak WEP initialization vector.
			"
	::= {wlsxTrapDefinitionsGroup 1102 }

	wlsxStaAssociatedToUnsecureAP NOTIFICATION-TYPE
		OBJECTS {wlsxTrapTime, wlsxTrapTargetAPBSSID,wlsxTrapTargetAPSSID,
				wlsxTrapAPMacAddress,wlsxTrapAPRadioNumber,
				wlsxTrapNodeMac,wlsxTrapAPLocation,
				wlsxTrapAPChannel,wlsxTrapRogueInfoURL,
				wlsxTrapAPBand}
		STATUS		current
		DESCRIPTION
			"			
			This trap indicates that an AM detected a client associated
			with a Rogue access point.
			"
	::= {wlsxTrapDefinitionsGroup 1103 }

	wlsxStaUnAssociatedFromUnsecureAP NOTIFICATION-TYPE
		OBJECTS {wlsxTrapTime, wlsxTrapTargetAPBSSID,wlsxTrapTargetAPSSID,
				wlsxTrapAPMacAddress,wlsxTrapAPRadioNumber,
				wlsxTrapNodeMac}
		STATUS		current
		DESCRIPTION
			"			
			This trap indicates that a previously detected rogue access point 
            association is no longer present.
			"
	::= {wlsxTrapDefinitionsGroup 1104 }

	wlsxAdhocNetworkBridgeDetected NOTIFICATION-TYPE
		OBJECTS {wlsxTrapTime, wlsxTrapSourceMac,wlsxTrapTargetAPBSSID,
				wlsxTrapTargetAPSSID,wlsxTrapAPMacAddress,
				wlsxTrapAPRadioNumber,wlsxTrapAPLocation,
				wlsxTrapAPChannel}
		STATUS		current
		DESCRIPTION
			"			
			This trap indicates that an AM has detected an Ad hoc
			network that is bridging to a wired network
			"
	::= {wlsxTrapDefinitionsGroup 1105 }

	wlsxInterferingApDetected NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapInterferingAPInfoURL,wlsxTrapAPBand}
		STATUS		current
		DESCRIPTION
			"			
			This trap indicates that an AP detected an access point classified as Interfering. The access point 
            is declared Interfering because it is neither authorized or classified as Rogue. 
			"
	::= {wlsxTrapDefinitionsGroup 1106 }

	wlsxPortUp NOTIFICATION-TYPE
		OBJECTS {wlsxTrapTime, wlsxTrapCardSlot,wlsxTrapPortNumber,
				wlsxTrapAdminStatus,wlsxTrapOperStatus}
		STATUS		deprecated
		DESCRIPTION
			"			
            This trap indicates that a Physical port is up.
        	"
	::= {wlsxTrapDefinitionsGroup 1107 }

	wlsxPortDown NOTIFICATION-TYPE
		OBJECTS {wlsxTrapTime, wlsxTrapCardSlot,wlsxTrapPortNumber,
				wlsxTrapAdminStatus,wlsxTrapOperStatus}
		STATUS		deprecated
		DESCRIPTION
			"			
            This trap indicates that a Physical port is Down.
        	"
	::= {wlsxTrapDefinitionsGroup 1108 }

	wlsxBSSIDIsUp NOTIFICATION-TYPE
		OBJECTS {wlsxTrapTime, wlsxTrapAPMacAddress,wlsxTrapAPRadioNumber,
				wlsxTrapAPBSSID,wlsxTrapAPName}
		STATUS		current
		DESCRIPTION
			"			
            A Trap which indicates that an access point BSSID is up.
        	"
	::= {wlsxTrapDefinitionsGroup 1109 }

	wlsxBSSIDIsDown NOTIFICATION-TYPE
		OBJECTS {wlsxTrapTime, wlsxTrapAPMacAddress,wlsxTrapAPRadioNumber,
				wlsxTrapAPBSSID,wlsxTrapAPName}
		STATUS		current
		DESCRIPTION
			"			
            A Trap which indicates that an access point BSSID is down.
        	"
	::= {wlsxTrapDefinitionsGroup 1110 }

	wlsxColdStart NOTIFICATION-TYPE
		OBJECTS {wlsxTrapTime}
		STATUS		current
		DESCRIPTION
			"			
            An enterprise version of cold start trap, which contains the controller time stamp.
        	"
	::= {wlsxTrapDefinitionsGroup 1111 }

	wlsxWarmStart NOTIFICATION-TYPE
		OBJECTS {wlsxTrapTime}
		STATUS		current
		DESCRIPTION
			"			
            An enterprise version of warm start trap, which contains the controller time stamp.
        	"
	::= {wlsxTrapDefinitionsGroup 1112 }

	wlsxAPImpersonation NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP detected AP Impersonation because the number of beacons seen has exceeded the expected number by the configured percentage threshold.
            The expected number is calculated based on the Beacon Interval Field in the Beacon frame.
			"
	::= {wlsxTrapDefinitionsGroup 1113 }

	wlsxInformQueueOverFlow NOTIFICATION-TYPE
		OBJECTS {wlsxTrapTime, wlsxTrapHostIp,wlsxTrapHostPort}
		STATUS		current
		DESCRIPTION
			"			
			This trap indicates that an Inform queue overflow condition occurred.
			"
	::= {wlsxTrapDefinitionsGroup 1114 }

	wlsxNAuthServerIsDown NOTIFICATION-TYPE
		OBJECTS {wlsxTrapTime, wlsxTrapAuthServerName,wlsxTrapAuthServerAddress}
		STATUS		current
		DESCRIPTION
			"			
            This trap indicates that an authentication server is down.
        	"
	::= {wlsxTrapDefinitionsGroup 1115 }

	wlsxCTSTransferError NOTIFICATION-TYPE
		OBJECTS {wlsxTrapTime, wlsxTrapCTSTransferType,wlsxTrapCTSURL}
		STATUS		current
		DESCRIPTION
			"			
            This trap indicates the status of the configuration transfer from the management station.
        	"
	::= {wlsxTrapDefinitionsGroup 1116 }

	wlsxCTSTransferSucceeded NOTIFICATION-TYPE
		OBJECTS {wlsxTrapTime, wlsxTrapCTSTransferType,wlsxTrapCTSURL}
		STATUS		current
		DESCRIPTION
			"			
            This trap indicates the status of the configuration transfer from the management station.
        	"
	::= {wlsxTrapDefinitionsGroup 1117 }

	wlsxConfigurationUpdateError NOTIFICATION-TYPE
		OBJECTS {wlsxTrapTime, wlsxTrapConfigurationId,wlsxTrapUpdateFailureReason,
				wlsxTrapUpdateFailedObj}
		STATUS		current
		DESCRIPTION
			"			
            This trap indicates the configuration update status.
        	"
	::= {wlsxTrapDefinitionsGroup 1118 }

	wlsxConfigurationUpdateSucceeded NOTIFICATION-TYPE
		OBJECTS {wlsxTrapTime, wlsxTrapConfigurationId}
		STATUS		current
		DESCRIPTION
			"			
            This trap indicates the configuration update status.
        	"
	::= {wlsxTrapDefinitionsGroup 1119 }

	wlsxGlobalConfigurationChangeNotification NOTIFICATION-TYPE
		OBJECTS {wlsxTrapTime, wlsxTrapConfigurationId,wlsxTrapGlobalConfigObj}
		STATUS		current
		DESCRIPTION
			"			
            This trap indicates that global configuration was modified on the controller.
        	"
	::= {wlsxTrapDefinitionsGroup 1120 }

	wlsxUserEntryChanged NOTIFICATION-TYPE
		OBJECTS {wlsxTrapTime, wlsxTrapTableGenNumber,wlsxTrapUserIpAddress,
				wlsxTrapUserPhyAddress,wlsxTrapTableEntryChangeType}
		STATUS		current
		DESCRIPTION
			"			
            This trap indicates that the user configuration has changed.
        	"
	::= {wlsxTrapDefinitionsGroup 1121 }

	wlsxAPBssidEntryChanged NOTIFICATION-TYPE
		OBJECTS {wlsxTrapTime, wlsxTrapTableGenNumber,wlsxTrapAPMacAddress,
				wlsxTrapAPRadioNumber,wlsxTrapAPBSSID,
				wlsxTrapTableEntryChangeType}
		STATUS		current
		DESCRIPTION
			"			
            This trap indicates that the BSSID configuration has changed.
        	"
	::= {wlsxTrapDefinitionsGroup 1122 }

	wlsxAPRadioEntryChanged NOTIFICATION-TYPE
		OBJECTS {wlsxTrapTime, wlsxTrapTableGenNumber,wlsxTrapAPMacAddress,
				wlsxTrapAPRadioNumber,wlsxTrapTableEntryChangeType}
		STATUS		current
		DESCRIPTION
			"			
            This trap indicates that the Radio configuration has changed.
        	"
	::= {wlsxTrapDefinitionsGroup 1123 }

	wlsxAPEntryChanged NOTIFICATION-TYPE
		OBJECTS {wlsxTrapTime, wlsxTrapTableGenNumber,wlsxTrapAPMacAddress,
				wlsxTrapTableEntryChangeType}
		STATUS		current
		DESCRIPTION
			"			
            This trap indicates that the AP configuration has changed.
        	"
	::= {wlsxTrapDefinitionsGroup 1124 }

	wlsxSwitchListEntryChanged NOTIFICATION-TYPE
		OBJECTS {wlsxTrapTime, wlsxTrapTableGenNumber,wlsxTrapSwitchIp,
				wlsxTrapTableEntryChangeType}
		STATUS		current
		DESCRIPTION
			"			
            This trap indicates that the controller list has changed.
        	"
	::= {wlsxTrapDefinitionsGroup 1125 }

	wlsxPortEntryChanged NOTIFICATION-TYPE
		OBJECTS {wlsxTrapTime, wlsxTrapTableGenNumber,wlsxTrapCardSlot,
				wlsxTrapPortNumber,wlsxTrapTableEntryChangeType}
		STATUS		current
		DESCRIPTION
			"			
            This trap indicates that the port configuration has changed.
        	"
	::= {wlsxTrapDefinitionsGroup 1126 }

	wlsxVlanEntryChanged NOTIFICATION-TYPE
		OBJECTS {wlsxTrapTime, wlsxTrapTableGenNumber,wlsxTrapVlanId,
				wlsxTrapTableEntryChangeType}
		STATUS		current
		DESCRIPTION
			"			
            This trap indicates that the VLAN configuration has changed.
        	"
	::= {wlsxTrapDefinitionsGroup 1127 }

	wlsxVlanInterfaceEntryChanged NOTIFICATION-TYPE
		OBJECTS {wlsxTrapTime, wlsxTrapTableGenNumber,wlsxTrapVlanId,
				wlsxTrapTableEntryChangeType}
		STATUS		current
		DESCRIPTION
			"			
            This trap indicates that the VLAN Interface configuration has changed.
        	"
	::= {wlsxTrapDefinitionsGroup 1128 }

	wlsxWindowsBridgeDetected NOTIFICATION-TYPE
		OBJECTS {wlsxTrapTime, wlsxTrapSourceMac,wlsxTrapTargetAPBSSID,
				wlsxTrapTargetAPSSID,wlsxTrapAPMacAddress,
				wlsxTrapAPRadioNumber,wlsxTrapAPLocation,
				wlsxTrapAPChannel,wlsxTrapAPBand}
		STATUS		current
		DESCRIPTION
			"			
			This trap indicates that an AM has detected a station
		        that is bridging from a wireless network 
                        to a wired network
			"
	::= {wlsxTrapDefinitionsGroup 1129 }

	wlsxLicenseEntryChanged NOTIFICATION-TYPE
		OBJECTS {wlsxTrapTime, wlsxTrapTableGenNumber,wlsxTrapLicenseId,
				wlsxTrapTableEntryChangeType}
		STATUS		current
		DESCRIPTION
			"			
            This trap indicates that the license table has changed.
        	"
	::= {wlsxTrapDefinitionsGroup 1130 }

	wlsxEsiServerChanged NOTIFICATION-TYPE
		OBJECTS {wlsxTrapTime, wlsxTrapTableGenNumber,wlsxTrapESIServerName,
				wlsxTrapTableEntryChangeType}
		STATUS		current
		DESCRIPTION
			"			
            This trap indicates that the ESI server table has changed.
        	"
	::= {wlsxTrapDefinitionsGroup 1131 }

	wlsxMonAPEntryChanged NOTIFICATION-TYPE
		OBJECTS {wlsxTrapTime, wlsxTrapTableGenNumber,wlsxTrapAPMacAddress,
				wlsxTrapAPRadioNumber,wlsxTrapTargetAPBSSID,
				wlsxTrapTableEntryChangeType}
		STATUS		current
		DESCRIPTION
			"			
            This trap indicates that a monitored AP entry changed
        	"
	::= {wlsxTrapDefinitionsGroup 1132 }

	wlsxMonStationEntryChanged NOTIFICATION-TYPE
		OBJECTS {wlsxTrapTime, wlsxTrapTableGenNumber,wlsxTrapAPMacAddress,
				wlsxTrapAPRadioNumber,wlsxTrapNodeMac,
				wlsxTrapTableEntryChangeType}
		STATUS		current
		DESCRIPTION
			"			
            This trap indicates that a monitored station entry changed
        	"
	::= {wlsxTrapDefinitionsGroup 1133 }

	wlsxSignAPNetstumbler NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match for Netstumbler from an access point.
			"
	::= {wlsxTrapDefinitionsGroup 1134 }

	wlsxSignStaNetstumbler NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match for Netstumbler from a Station.
			"
	::= {wlsxTrapDefinitionsGroup 1135 }

	wlsxSignAPAsleap NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match for ASLEAP from an access point.
			"
	::= {wlsxTrapDefinitionsGroup 1136 }

	wlsxSignStaAsleap NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match for ASLEAP from a Station.
			"
	::= {wlsxTrapDefinitionsGroup 1137 }

	wlsxSignAPAirjack NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match for AirJack from an access point.
			"
	::= {wlsxTrapDefinitionsGroup 1138 }

	wlsxSignStaAirjack NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match for AirJack from a Station.
			"
	::= {wlsxTrapDefinitionsGroup 1139 }

	wlsxSignAPNullProbeResp NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match for Null-Probe-Response from an access point.
			"
	::= {wlsxTrapDefinitionsGroup 1140 }

	wlsxSignStaNullProbeResp NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match for Null-Probe-Response from a Station.
			"
	::= {wlsxTrapDefinitionsGroup 1141 }

	wlsxSignAPDeauthBcast NOTIFICATION-TYPE
		OBJECTS {wlsxTrapTime, wlsxTrapSignatureName,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AP detected a signature match for Deauth-Broadcast from an access point.
			"
	::= {wlsxTrapDefinitionsGroup 1142 }

	wlsxSignStaDeauthBcast NOTIFICATION-TYPE
		OBJECTS {wlsxTrapTime, wlsxTrapSignatureName,wlsxTrapSourceMac,
				wlsxTrapSnr,wlsxTrapAPMacAddress,
				wlsxTrapAPRadioNumber,wlsxTrapAPLocation}
		STATUS		current
		DESCRIPTION
			"			
			This trap indicates that an AP detected a signature match for Deauth-Broadcast from a Station.
			"
	::= {wlsxTrapDefinitionsGroup 1143 }

	wlsxWindowsBridgeDetectedAP NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
			This trap indicates that an AP is detecting an access point that is bridging from a wireless network
            to a wired network.
			"
	::= {wlsxTrapDefinitionsGroup 1144 }

	wlsxWindowsBridgeDetectedSta NOTIFICATION-TYPE
		OBJECTS {wlsxTrapTime, wlsxTrapSourceMac,wlsxTrapTargetAPBSSID,
				wlsxTrapTargetAPSSID,wlsxTrapAPMacAddress,
				wlsxTrapAPRadioNumber,wlsxTrapAPLocation,
				wlsxTrapAPChannel,wlsxTrapAPBand}
		STATUS		current
		DESCRIPTION
			"			
			This trap indicates that an AP is detecting a station that is bridging from a wireless network
            to a wired network.
			"
	::= {wlsxTrapDefinitionsGroup 1145 }

	wlsxAdhocNetworkBridgeDetectedAP NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel}
		STATUS		current
		DESCRIPTION
			"			
			This trap indicates that an AM has detected an Ad hoc
			network that is bridging to a wired network
			"
	::= {wlsxTrapDefinitionsGroup 1146 }

	wlsxAdhocNetworkBridgeDetectedSta NOTIFICATION-TYPE
		OBJECTS {wlsxTrapTime, wlsxTrapSourceMac,wlsxTrapTargetAPBSSID,
				wlsxTrapTargetAPSSID,wlsxTrapAPMacAddress,
				wlsxTrapAPRadioNumber,wlsxTrapAPLocation,
				wlsxTrapAPChannel}
		STATUS		current
		DESCRIPTION
			"			
			This trap indicates that an AM has detected an Ad hoc
			network that is bridging to a wired network
			"
	::= {wlsxTrapDefinitionsGroup 1147 }

	wlsxDisconnectStationAttackAP NOTIFICATION-TYPE
		OBJECTS {wlsxTrapTime, wlsxTrapFrameType,wlsxTrapTargetAPBSSID,
				wlsxTrapTargetAPSSID,wlsxTrapSnr,
				wlsxTrapAPMacAddress,wlsxTrapAPRadioNumber,
				wlsxTrapAPLocation}
		STATUS		current
		DESCRIPTION
			"			
			This trap indicates that an AM detected a station disconnect 
            attack.
			"
	::= {wlsxTrapDefinitionsGroup 1148 }

	wlsxDisconnectStationAttackSta NOTIFICATION-TYPE
		OBJECTS {wlsxTrapTime, wlsxTrapFrameType,wlsxTrapSourceMac,
				wlsxTrapSnr,wlsxTrapAPMacAddress,
				wlsxTrapAPRadioNumber,wlsxTrapAPLocation}
		STATUS		current
		DESCRIPTION
			"			
			This trap indicates that an AM detected a station Disconnect 
            attack.
			"
	::= {wlsxTrapDefinitionsGroup 1149 }

	wlsxSuspectUnsecureAPDetected NOTIFICATION-TYPE
		OBJECTS {wlsxTrapTime, wlsxTrapTargetAPBSSID,wlsxTrapTargetAPSSID,
				wlsxTrapAPRadioNumber,wlsxTrapMatchedMac,
				wlsxTrapMatchedIp,wlsxTrapConfidenceLevel,
				wlsxTrapAPLocation,wlsxTrapRogueInfoURL,
				wlsxTrapMatchedIpv6}
		STATUS		current
		DESCRIPTION
			"			This trap indicates that an access point, classified as Suspected Rogue, has been
                detected by a Controller. The AP is suspected to be rogue, 
                with the supplied confidence level, because it was matched to 
                the wired MAC address. 
			"
	::= {wlsxTrapDefinitionsGroup 1150 }

	wlsxSuspectUnsecureAPResolved NOTIFICATION-TYPE
		OBJECTS {wlsxTrapTime, wlsxTrapTargetAPBSSID,wlsxTrapTargetAPSSID,
				wlsxTrapAPRadioNumber}
		STATUS		current
		DESCRIPTION
			"			
		This trap indicates that a previously detected access point, classified Suspected 
                Rogue, is either no longer present in the network or
                has changed its state.
			"
	::= {wlsxTrapDefinitionsGroup 1151 }

	wlsxConfigurationLicenseMismatch NOTIFICATION-TYPE
		OBJECTS {wlsxTrapTime, wlsxTrapConfigurationId,wlsxTrapMissingLicenses}
		STATUS		current
		DESCRIPTION
			"			
            This trap indicates the configuration update status in the case
            where some configuration could not be applied due to missing licenses.
        	"
	::= {wlsxTrapDefinitionsGroup 1152 }

	wlsxVoiceCdrBufferThresholdReached NOTIFICATION-TYPE
		OBJECTS {wlsxTrapTime, wlsxVoiceCurrentNumCdr}
		STATUS		current
		DESCRIPTION
			"			
            This trap indicates that the CDR buffer threshold has been reached
        	"
	::= {wlsxTrapDefinitionsGroup 1153 }

	wlsxTunnelUp NOTIFICATION-TYPE
		OBJECTS {wlsxTrapTime, wlsxTrapTunnelId,wlsxTrapTunnelUpReason,
				wlsxTrapTunnelStatus}
		STATUS		current
		DESCRIPTION
			"			
            This trap indicates that a tunnel interface is up.
        	"
	::= {wlsxTrapDefinitionsGroup 1154 }

	wlsxTunnelDown NOTIFICATION-TYPE
		OBJECTS {wlsxTrapTime, wlsxTrapTunnelId,wlsxTrapTunnelDownReason,
				wlsxTrapTunnelStatus}
		STATUS		current
		DESCRIPTION
			"			
            This trap indicates that a tunnel interface is down.
        	"
	::= {wlsxTrapDefinitionsGroup 1155 }

	wlsxMeshNodeEntryChanged NOTIFICATION-TYPE
		OBJECTS {wlsxTrapTime, wlsxTrapTableGenNumber,wlsxTrapAPMacAddress,
				wlsxTrapTableEntryChangeType}
		STATUS		current
		DESCRIPTION
			"			
            This trap indicates that the mesh node configuration has changed.
        	"
	::= {wlsxTrapDefinitionsGroup 1156 }

	wlsxHtGreenfieldSupported NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
	    This trap indicates that an AP detected an access point that supports HT Greenfield mode.
		"
	::= {wlsxTrapDefinitionsGroup 1157 }

	wlsxHT40MHzIntoleranceAP NOTIFICATION-TYPE
		OBJECTS {wlsxTrapTime, wlsxTrapTargetAPBSSID,wlsxTrapTargetAPSSID,
				wlsxTrapAPMacAddress,wlsxTrapAPRadioNumber,
				wlsxTrapAPLocation,wlsxTrapAPChannel,
				wlsxTrapAPBand}
		STATUS		current
		DESCRIPTION
			"			
	    This trap indicates that an AP is detecting an access point with the HT 40MHz intolerance setting.
		"
	::= {wlsxTrapDefinitionsGroup 1158 }

	wlsxHT40MHzIntoleranceSta NOTIFICATION-TYPE
		OBJECTS {wlsxTrapTime, wlsxTrapSourceMac,wlsxTrapSnr,
				wlsxTrapAPChannel,wlsxTrapFrameType,
				wlsxTrapAPMacAddress,wlsxTrapAPRadioNumber,
				wlsxTrapAPLocation,wlsxTrapAPBand}
		STATUS		current
		DESCRIPTION
			"			
		This trap indicates that the system is detecting an HT 40MHz Intolerance setting from a Station.
		"
	::= {wlsxTrapDefinitionsGroup 1159 }

	wlsxNAuthServerAllInService NOTIFICATION-TYPE
		OBJECTS {wlsxTrapTime, wlsxTrapESIServerGrpName}
		STATUS		current
		DESCRIPTION
			"			
            This trap indicates that all authentication servers is a server group are brought back in service.
        	"
	::= {wlsxTrapDefinitionsGroup 1160 }

	wlsxNAdhocNetwork NOTIFICATION-TYPE
		OBJECTS {wlsxTrapTime, wlsxTrapSourceMac,wlsxTrapTargetAPBSSID,
				wlsxTrapTargetAPSSID,wlsxTrapSnr,
				wlsxTrapAPMacAddress,wlsxTrapAPRadioNumber,
				wlsxTrapAPLocation,wlsxTrapAPChannel,
				wlsxTrapAPBand}
		STATUS		current
		DESCRIPTION
			"			
			This trap indicates that an AP detected an ad hoc 
			network where a station is connected to an ad hoc access point.
			"
	::= {wlsxTrapDefinitionsGroup 1161 }

	wlsxNAdhocNetworkBridgeDetectedAP NOTIFICATION-TYPE
		OBJECTS {wlsxTrapTime, wlsxTrapTargetAPBSSID,wlsxTrapTargetAPSSID,
				wlsxTrapSnr,wlsxTrapAPMacAddress,
				wlsxTrapAPRadioNumber,wlsxTrapAPLocation,
				wlsxTrapAPChannel,wlsxTrapAPBand}
		STATUS		current
		DESCRIPTION
			"			
			This trap indicates that an AP detected an ad hoc
			network that is bridging to a wired network.
			"
	::= {wlsxTrapDefinitionsGroup 1162 }

	wlsxNAdhocNetworkBridgeDetectedSta NOTIFICATION-TYPE
		OBJECTS {wlsxTrapTime, wlsxTrapSourceMac,wlsxTrapTargetAPBSSID,
				wlsxTrapTargetAPSSID,wlsxTrapSnr,
				wlsxTrapAPMacAddress,wlsxTrapAPRadioNumber,
				wlsxTrapAPLocation,wlsxTrapAPChannel,
				wlsxTrapAPBand}
		STATUS		current
		DESCRIPTION
			"			
			This trap indicates that an AP detected an ad hoc
			network that is bridging to a wired network.
			"
	::= {wlsxTrapDefinitionsGroup 1163 }

	wlsxNAuthMaxXsecUserEntries NOTIFICATION-TYPE
		OBJECTS {wlsxTrapTime}
		STATUS		current
		DESCRIPTION
			"			
            A trap which indicates that the xSec user limit is reached.
        	"
	::= {wlsxTrapDefinitionsGroup 1164 }

	wlsxNVpnMaxSessions NOTIFICATION-TYPE
		OBJECTS {wlsxTrapTime}
		STATUS		current
		DESCRIPTION
			"			
            A trap which indicates that the VPN session limit is reached.
        	"
	::= {wlsxTrapDefinitionsGroup 1165 }

	wlsxNRapExpiredPSK NOTIFICATION-TYPE
		OBJECTS {wlsxTrapTime, wlsxTrapAPIpAddress,wlsxTrapApSerialNumber}
		STATUS		current
		DESCRIPTION
			"			
            A trap which indicates that the RAP is using the Expired PSK.
        	"
	::= {wlsxTrapDefinitionsGroup 1166 }

	wlsxNRapWarnExpiredPSK NOTIFICATION-TYPE
		OBJECTS {wlsxTrapTime, wlsxTrapTimeStr}
		STATUS		current
		DESCRIPTION
			"			
            A trap which indicates that the Cached IKE PSK for RAPs will expire soon.
        	"
	::= {wlsxTrapDefinitionsGroup 1167 }

	wlsxNConnectionResetWithLocal NOTIFICATION-TYPE
		OBJECTS {wlsxTrapTime, wlsxTrapMasterName,wlsxTrapMasterIp,
				wlsxTrapLocalName,wlsxTrapLocalIp,
				wlsxTrapTimeStr}
		STATUS		obsolete
		DESCRIPTION
			"			
            A trap which indicates that tcp connection between master controller and local controller has been lost.
        	"
	::= {wlsxTrapDefinitionsGroup 1168 }

	wlsxNApOnBackupController NOTIFICATION-TYPE
		OBJECTS {wlsxTrapTime, wlsxTrapAPMacAddress,wlsxTrapBackupControllerIp,
				wlsxTrapPrimaryControllerIp}
		STATUS		current
		DESCRIPTION
			"			
            A trap which indicates that the AP has registered with the backup controller.
        	"
	::= {wlsxTrapDefinitionsGroup 1169 }

	wlsxClientFloodAttack NOTIFICATION-TYPE
		OBJECTS {wlsxTrapTime, wlsxTrapAPMacAddress,wlsxTrapAPRadioNumber,
				wlsxTrapAPLocation}
		STATUS		current
		DESCRIPTION
			"			
			This trap indicates that the number of potential fake clients detected by 
			an AP has exceeded the configured IDS threshold. This is the total number of fake clients observed across all bands.
			"
	::= {wlsxTrapDefinitionsGroup 1170 }

	wlsxValidClientNotUsingEncryption NOTIFICATION-TYPE
		OBJECTS {wlsxTrapTime, wlsxTrapTargetAPBSSID,wlsxTrapSourceMac,
				wlsxTrapReceiverMac,wlsxTrapNodeMac,
				wlsxTrapSnr,wlsxTrapAPMacAddress,
				wlsxTrapAPRadioNumber,wlsxTrapAPLocation,
				wlsxTrapAPChannel}
		STATUS		current
		DESCRIPTION
			"			
		    This trap indicates that an AP detected an unencrypted data frame between a valid client and an access point.
			"
	::= {wlsxTrapDefinitionsGroup 1171 }

	wlsxAdhocUsingValidSSID NOTIFICATION-TYPE
		OBJECTS {wlsxTrapTime, wlsxTrapTargetAPBSSID,wlsxTrapTargetAPSSID,
				wlsxTrapSnr,wlsxTrapAPMacAddress,
				wlsxTrapAPRadioNumber,wlsxTrapAPLocation,
				wlsxTrapAPChannel}
		STATUS		current
		DESCRIPTION
			"			
			This trap indicates that an AP detected an ad hoc network using a valid/protected SSID.
			"
	::= {wlsxTrapDefinitionsGroup 1172 }

	wlsxAPSpoofingDetected NOTIFICATION-TYPE
		OBJECTS {wlsxTrapTime, wlsxTrapTargetAPBSSID,wlsxTrapSourceMac,
				wlsxTrapReceiverMac,wlsxTrapSpoofedFrameType,
				wlsxTrapSnr,wlsxTrapAPMacAddress,
				wlsxTrapAPRadioNumber,wlsxTrapAPLocation,
				wlsxTrapAPChannel,wlsxTrapAPBand}
		STATUS		current
		DESCRIPTION
			"			
			This trap indicates that an AP detected that one of its virtual APs is being spoofed using MAC spoofing.
			"
	::= {wlsxTrapDefinitionsGroup 1173 }

	wlsxClientAssociatingOnWrongChannel NOTIFICATION-TYPE
		OBJECTS {wlsxTrapTime, wlsxTrapTargetAPBSSID,wlsxTrapSourceMac,
				wlsxTrapReceiverMac,wlsxTrapSpoofedFrameType,
				wlsxTrapSnr,wlsxTrapAPMacAddress,
				wlsxTrapAPRadioNumber,wlsxTrapAPLocation,
				wlsxTrapAPChannel,wlsxTrapAPBand}
		STATUS		current
		DESCRIPTION
			"			
			This trap indicates that an AP detected a client trying to associate to one of its BSSIDs on the wrong channel.  This can be a sign that the BSSID is 
            being spoofed in order to fool the client into thinking the AP is operating on another channel.
			"
	::= {wlsxTrapDefinitionsGroup 1174 }

	wlsxNDisconnectStationAttack NOTIFICATION-TYPE
		OBJECTS {wlsxTrapTime, wlsxTrapTargetAPBSSID,wlsxTrapTargetAPSSID,
				wlsxTrapSourceMac,wlsxTrapSnr,
				wlsxTrapAPMacAddress,wlsxTrapAPRadioNumber,
				wlsxTrapAPLocation,wlsxTrapAPChannel,
				wlsxTrapAPBand}
		STATUS		current
		DESCRIPTION
			"			
			This trap indicates that an AP has determined that a client is under Disconnect Attack because the rate of Assoc/Reassoc Response packets
            received by that client exceeds the configured threshold.
			"
	::= {wlsxTrapDefinitionsGroup 1175 }

	wlsxNStaUnAssociatedFromUnsecureAP NOTIFICATION-TYPE
		OBJECTS {wlsxTrapTime, wlsxTrapTargetAPBSSID,wlsxTrapTargetAPSSID,
				wlsxTrapAPMacAddress,wlsxTrapAPRadioNumber,
				wlsxTrapNodeMac,wlsxTrapAPLocation,
				wlsxTrapAPChannel,wlsxTrapAPBand}
		STATUS		current
		DESCRIPTION
			"			
			This trap indicates that an AP that had previously detected a client association to a Rogue access point is no longer detecting that association.
			"
	::= {wlsxTrapDefinitionsGroup 1176 }

	wlsxOmertaAttack NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
			This trap indicates that an AP detected an Omerta attack.
			"
	::= {wlsxTrapDefinitionsGroup 1177 }

	wlsxTKIPReplayAttack NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a possible TKIP replay attack. If successful this could be the precursor to more
			advanced attacks.
			"
	::= {wlsxTrapDefinitionsGroup 1178 }

	wlsxChopChopAttack NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a ChopChop attack.
			"
	::= {wlsxTrapDefinitionsGroup 1179 }

	wlsxFataJackAttack NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
			This trap indicates that an AP detected a FATA-Jack attack.
			"
	::= {wlsxTrapDefinitionsGroup 1180 }

	wlsxInvalidAddressCombination NOTIFICATION-TYPE
		OBJECTS {wlsxTrapTime, wlsxTrapAPMacAddress,wlsxTrapAPRadioNumber,
				wlsxTrapAPLocation,wlsxTrapSourceMac,
				wlsxTrapReceiverMac,wlsxTrapAPChannel,
				wlsxTrapSnr,wlsxTrapAPBand}
		STATUS		current
		DESCRIPTION
			"			
			This trap indicates that an AP detected an invalid source and destination combination.
			"
	::= {wlsxTrapDefinitionsGroup 1181 }

	wlsxValidClientMisassociation NOTIFICATION-TYPE
		OBJECTS {wlsxTrapTime, wlsxTrapTargetAPBSSID,wlsxTrapTargetAPSSID,
				wlsxTrapNodeMac,wlsxTrapAssociationType,
				wlsxTrapSnr,wlsxTrapAPMacAddress,
				wlsxTrapAPRadioNumber,wlsxTrapAPLocation,
				wlsxTrapAPChannel,wlsxTrapAPBand}
		STATUS		current
		DESCRIPTION
			"			
			This trap indicates that an AP detected a misassociation between a valid client and an unsafe AP.
			"
	::= {wlsxTrapDefinitionsGroup 1182 }

	wlsxMalformedHTIEDetected NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a malformed HT Information Element. This can be the result of a misbehaving wireless driver or it may be an indication of a new wireless attack. 
			"
	::= {wlsxTrapDefinitionsGroup 1183 }

	wlsxMalformedAssocReqDetected NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a malformed association request with a NULL SSID.
			"
	::= {wlsxTrapDefinitionsGroup 1184 }

	wlsxOverflowIEDetected NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a management frame with a malformed information element. The declared length of the element is larger than the entire frame containing the element. This may be used to corrupt or crash wireless drivers. 
			"
	::= {wlsxTrapDefinitionsGroup 1185 }

	wlsxOverflowEAPOLKeyDetected NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
			This trap indicates that an AP detected a key in an EAPOL Key message with a specified length greater than the length of the entire message.
			"
	::= {wlsxTrapDefinitionsGroup 1186 }

	wlsxMalformedFrameLargeDurationDetected NOTIFICATION-TYPE
		OBJECTS {wlsxTrapTime, wlsxTrapAPMacAddress,wlsxTrapAPRadioNumber,
				wlsxTrapAPLocation,wlsxTrapSourceMac,
				wlsxTrapAPChannel,wlsxTrapSnr,
				wlsxTrapAPBand}
		STATUS		current
		DESCRIPTION
			"			
			This trap indicates that an AP detected an unusually large duration in a wireless frame. This may be an attempt to block other devices from transmitting.
			"
	::= {wlsxTrapDefinitionsGroup 1187 }

	wlsxMalformedFrameWrongChannelDetected NOTIFICATION-TYPE
		OBJECTS {wlsxTrapTime, wlsxTrapAPMacAddress,wlsxTrapAPRadioNumber,
				wlsxTrapAPLocation,wlsxTrapSourceMac,
				wlsxTrapTargetAPBSSID,wlsxTrapTargetAPSSID,
				wlsxTrapTargetAPChannel,wlsxTrapAPChannel,
				wlsxTrapSnr,wlsxTrapAPBand,
				wlsxTrapTargetAPBand}
		STATUS		current
		DESCRIPTION
			"			
			This trap indicates that an AP detected a beacon on one channel advertising another channel. This could be an attempt to lure clients away from a valid AP.
			"
	::= {wlsxTrapDefinitionsGroup 1188 }

	wlsxMalformedAuthFrame NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
			This trap indicates that an AP detected an authentication frame with
            either a bad algorithm (similar to Fata-Jack) or a bad transaction.
			"
	::= {wlsxTrapDefinitionsGroup 1189 }

	wlsxCTSRateAnomaly NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that the rate of CTS packets 
            received by an AP exceeds the configured IDS threshold.
			"
	::= {wlsxTrapDefinitionsGroup 1190 }

	wlsxRTSRateAnomaly NOTIFICATION-TYPE
		OBJECTS {wlsxTrapTime, wlsxTrapAPMacAddress,wlsxTrapAPRadioNumber,
				wlsxTrapAPLocation,wlsxTrapAPChannel,
				wlsxTrapAPBand}
		STATUS		current
		DESCRIPTION
			"			
			This trap indicates that the rate of RTS packets 
            received by an AP exceeds the configured IDS threshold.
			"
	::= {wlsxTrapDefinitionsGroup 1191 }

	wlsxNRogueAPDetected NOTIFICATION-TYPE
		OBJECTS {wlsxTrapTime, wlsxTrapTargetAPBSSID,wlsxTrapTargetAPSSID,
				wlsxTrapAPChannel,wlsxTrapAPBand}
		STATUS		current
		DESCRIPTION
			"			
				This trap indicates that an unauthorized access point is connected to the wired network. The access point is 
                classified as Rogue by the system.
			"
	::= {wlsxTrapDefinitionsGroup 1192 }

	wlsxNRogueAPResolved NOTIFICATION-TYPE
		OBJECTS {wlsxTrapTime, wlsxTrapTargetAPBSSID,wlsxTrapTargetAPSSID,
				wlsxTrapAPChannel,wlsxTrapAPBand}
		STATUS		current
		DESCRIPTION
			"			
                This trap indicates that a previously detected access point, classified as Rogue,
                is either no longer present in the network or it changed its state.
			"
	::= {wlsxTrapDefinitionsGroup 1193 }

	wlsxNeighborAPDetected NOTIFICATION-TYPE
		OBJECTS {wlsxTrapTime, wlsxTrapTargetAPBSSID,wlsxTrapTargetAPSSID,
				wlsxTrapAPChannel,wlsxTrapAPBand}
		STATUS		current
		DESCRIPTION
			"			
			This trap indicates that an access point has been classified as a Neighbor by the system. 
			"
	::= {wlsxTrapDefinitionsGroup 1194 }

	wlsxNInterferingAPDetected NOTIFICATION-TYPE
		OBJECTS {wlsxTrapTime, wlsxTrapTargetAPBSSID,wlsxTrapTargetAPSSID,
				wlsxTrapAPChannel,wlsxTrapAPBand}
		STATUS		current
		DESCRIPTION
			"			
			This trap indicates that an access point has been classified as Interfering by the system. The access point 
            is declared Interfering because it is not authorized, nor has it been classified as a Rogue. 
			"
	::= {wlsxTrapDefinitionsGroup 1195 }

	wlsxNSuspectRogueAPDetected NOTIFICATION-TYPE
		OBJECTS {wlsxTrapTime, wlsxTrapTargetAPBSSID,wlsxTrapTargetAPSSID,
				wlsxTrapAPChannel,wlsxTrapConfidenceLevel,
				wlsxTrapAPBand}
		STATUS		current
		DESCRIPTION
			"			
		This trap indicates that an access point, classified as Suspected Rogue, is 
                detected by the system. The AP is suspected to be rogue 
                with the supplied confidence level. 
			"
	::= {wlsxTrapDefinitionsGroup 1196 }

	wlsxNSuspectRogueAPResolved NOTIFICATION-TYPE
		OBJECTS {wlsxTrapTime, wlsxTrapTargetAPBSSID,wlsxTrapTargetAPSSID,
				wlsxTrapAPChannel,wlsxTrapAPBand}
		STATUS		current
		DESCRIPTION
			"			
		This trap indicates that a previously detected access point, classified as Suspected 
                Rogue, is either no longer present in the network or
                has changed its state.
			"
	::= {wlsxTrapDefinitionsGroup 1197 }

	wlsxBlockAckAttackDetected NOTIFICATION-TYPE
		OBJECTS {wlsxTrapTime, wlsxTrapAPMacAddress,wlsxTrapAPRadioNumber,
				wlsxTrapAPLocation,wlsxTrapSourceMac,
				wlsxTrapReceiverMac,wlsxTrapTargetAPBSSID,
				wlsxTrapAPChannel,wlsxTrapSnr,
				wlsxTrapAPBand}
		STATUS		current
		DESCRIPTION
			"			
        This trap indicates that an attempt has been made to deny service to
        the source address by spoofing a block ACK add request that sets a
        sequence number window outside the currently used window.
        	"
	::= {wlsxTrapDefinitionsGroup 1198 }

	wlsxHotspotterAttackDetected NOTIFICATION-TYPE
		OBJECTS {wlsxTrapTime, wlsxTrapAPMacAddress,wlsxTrapAPRadioNumber,
				wlsxTrapAPLocation,wlsxTrapNodeMac,
				wlsxTrapSourceMac,wlsxTrapTargetAPBSSID,
				wlsxTrapAPChannel,wlsxTrapSnr,
				wlsxTrapTargetAPSSID,wlsxTrapAPBand}
		STATUS		current
		DESCRIPTION
			"			
        This trap indicates that a new AP has appeared immediately following a client probe request.
        This is indicative of the Hotspotter tool or similar that attempts to trap clients with a fake
        hotspot or other wireless network.
        	"
	::= {wlsxTrapDefinitionsGroup 1199 }

	wlsxNSignatureMatch NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match in a frame.
			"
	::= {wlsxTrapDefinitionsGroup 1200 }

	wlsxNSignatureMatchNetstumbler NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Netstumbler in a frame.
			"
	::= {wlsxTrapDefinitionsGroup 1201 }

	wlsxNSignatureMatchAsleap NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for ASLEAP in a frame.
			"
	::= {wlsxTrapDefinitionsGroup 1202 }

	wlsxNSignatureMatchAirjack NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Airjack in a frame.
			"
	::= {wlsxTrapDefinitionsGroup 1203 }

	wlsxNSignatureMatchNullProbeResp NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Null-Probe-Response in a frame.
			"
	::= {wlsxTrapDefinitionsGroup 1204 }

	wlsxNSignatureMatchDeauthBcast NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Deauth-Broadcast in a frame.
			"
	::= {wlsxTrapDefinitionsGroup 1205 }

	wlsxNSignatureMatchDisassocBcast NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Disassoc-Broadcast in a frame.
			"
	::= {wlsxTrapDefinitionsGroup 1206 }

	wlsxNSignatureMatchWellenreiter NOTIFICATION-TYPE
		OBJECTS {wlsxTrapTime, wlsxTrapTargetAPBSSID,wlsxTrapTransmitterMac,
				wlsxTrapReceiverMac,wlsxTrapSignatureName,
				wlsxTrapSnr,wlsxTrapAPMacAddress,
				wlsxTrapAPRadioNumber,wlsxTrapAPLocation,
				wlsxTrapAPChannel,wlsxTrapAPBand}
		STATUS		current
		DESCRIPTION
			"			
			This trap indicates that an AP detected a signature match for Wellenreiter in a frame.
			"
	::= {wlsxTrapDefinitionsGroup 1207 }

	wlsxAPDeauthContainment NOTIFICATION-TYPE
		OBJECTS {wlsxTrapTime, wlsxTrapTargetAPBSSID,wlsxTrapNodeMac,
				wlsxTrapAPChannel,wlsxTrapAPMacAddress,
				wlsxTrapAPRadioNumber,wlsxTrapAPLocation,
				wlsxTrapAPBand}
		STATUS		current
		DESCRIPTION
			"			
	This trap indicates that an AP has attempted to contain an access point by disconnecting its client.
      	"
	::= {wlsxTrapDefinitionsGroup 1208 }

	wlsxClientDeauthContainment NOTIFICATION-TYPE
		OBJECTS {wlsxTrapTime, wlsxTrapNodeMac,wlsxTrapTargetAPBSSID,
				wlsxTrapAPChannel,wlsxTrapAPMacAddress,
				wlsxTrapAPRadioNumber,wlsxTrapAPLocation,
				wlsxTrapAPBand}
		STATUS		current
		DESCRIPTION
			"			
	This trap indicates that an AP has attempted to contain a client by disconnecting it from the AP that it is associated with.
      	"
	::= {wlsxTrapDefinitionsGroup 1209 }

	wlsxAPWiredContainment NOTIFICATION-TYPE
		OBJECTS {wlsxTrapTime, wlsxTrapTargetAPBSSID,wlsxTrapNodeMac,
				wlsxTrapDeviceIpAddress,wlsxTrapDeviceMac,
				wlsxTrapAPMacAddress,wlsxTrapAPRadioNumber,
				wlsxTrapAPLocation,wlsxTrapDeviceIpv6Address}
		STATUS		current
		DESCRIPTION
			"			
	This trap indicates that an AP has attempted to contain an access point by disrupting traffic to its client on the wired interface.
      	"
	::= {wlsxTrapDefinitionsGroup 1210 }

	wlsxClientWiredContainment NOTIFICATION-TYPE
		OBJECTS {wlsxTrapTime, wlsxTrapNodeMac,wlsxTrapTargetAPBSSID,
				wlsxTrapDeviceIpAddress,wlsxTrapDeviceMac,
				wlsxTrapAPMacAddress,wlsxTrapAPRadioNumber,
				wlsxTrapAPLocation,wlsxTrapDeviceIpv6Address}
		STATUS		current
		DESCRIPTION
			"			
	This trap indicates that an AP has attempted to contain a client by disrupting traffic to it on the wired interface.
      	"
	::= {wlsxTrapDefinitionsGroup 1211 }

	wlsxAPTaggedWiredContainment NOTIFICATION-TYPE
		OBJECTS {wlsxTrapTime, wlsxTrapTargetAPBSSID,wlsxTrapNodeMac,
				wlsxTrapDeviceIpAddress,wlsxTrapDeviceMac,
				wlsxTrapVlanId,wlsxTrapAPMacAddress,
				wlsxTrapAPRadioNumber,wlsxTrapAPLocation,
				wlsxTrapDeviceIpv6Address}
		STATUS		current
		DESCRIPTION
			"			
	This trap indicates that an AP has attempted to contain an access point by disrupting traffic to its client on the wired interface.
      	"
	::= {wlsxTrapDefinitionsGroup 1212 }

	wlsxClientTaggedWiredContainment NOTIFICATION-TYPE
		OBJECTS {wlsxTrapTime, wlsxTrapNodeMac,wlsxTrapTargetAPBSSID,
				wlsxTrapDeviceIpAddress,wlsxTrapDeviceMac,
				wlsxTrapVlanId,wlsxTrapAPMacAddress,
				wlsxTrapAPRadioNumber,wlsxTrapAPLocation,
				wlsxTrapDeviceIpv6Address}
		STATUS		current
		DESCRIPTION
			"			
	This trap indicates that an AP has attempted to contain a client by disrupting traffic to it on the wired interface.
      	"
	::= {wlsxTrapDefinitionsGroup 1213 }

	wlsxTarpitContainment NOTIFICATION-TYPE
		OBJECTS {wlsxTrapTime, wlsxTrapTargetAPBSSID,wlsxTrapNodeMac,
				wlsxTrapAPChannel,wlsxTrapTargetAPChannel,
				wlsxTrapSourceMac,wlsxTrapAPMacAddress,
				wlsxTrapAPRadioNumber,wlsxTrapAPLocation,
				wlsxTrapAPBand,wlsxTrapTargetAPBand}
		STATUS		current
		DESCRIPTION
			"			
	This trap indicates that an AP has attempted to contain an access point by moving a client that is attempting to associate to it to a tarpit.
      	"
	::= {wlsxTrapDefinitionsGroup 1214 }

	wlsxVoiceClientLocationUpdate NOTIFICATION-TYPE
		OBJECTS {wlsxTrapTime, wlsxTrapVcIpAddress,wlsxTrapVcMacAddress,
				wlsxTrapSwitchIp,wlsxTrapAPName,
				wlsxTrapAPMacAddress,wlsxTrapApMode,
				wlsxTrapAPLocation}
		STATUS		current
		DESCRIPTION
			"			
            This trap indicates that the location of voice client has been changed.
        	"
	::= {wlsxTrapDefinitionsGroup 1215 }

	wlsxAPChannelChange NOTIFICATION-TYPE
		OBJECTS {wlsxTrapTime, wlsxTrapAPChannel,wlsxTrapAPChannelSec,
				wlsxTrapAPPrevChannel,wlsxTrapAPPrevChannelSec,
				wlsxTrapAPMacAddress,wlsxTrapAPRadioNumber,
				wlsxTrapAPLocation,wlsxTrapAPARMChangeReason,
				wlsxTrapAPHTMode,wlsxTrapAPPhyType,
				wlsxTrapAPPrevHTMode,wlsxTrapAPPrevPhyType}
		STATUS		current
		DESCRIPTION
			"			
            This trap indicates that an AP changed its channel.
      	"
	::= {wlsxTrapDefinitionsGroup 1216 }

	wlsxAPPowerChange NOTIFICATION-TYPE
		OBJECTS {wlsxTrapTime, wlsxTrapAPTxPower,wlsxTrapAPPrevTxPower,
				wlsxTrapAPMacAddress,wlsxTrapAPRadioNumber,
				wlsxTrapAPLocation}
		STATUS		current
		DESCRIPTION
			"			
	This trap indicates that an AP changed its transmit power level.
      	"
	::= {wlsxTrapDefinitionsGroup 1217 }

	wlsxAPModeChange NOTIFICATION-TYPE
		OBJECTS {wlsxTrapTime, wlsxTrapAPCurMode,wlsxTrapAPPrevMode,
				wlsxTrapAPMacAddress,wlsxTrapAPRadioNumber,
				wlsxTrapAPLocation}
		STATUS		current
		DESCRIPTION
			"			
	This trap indicates that an AP changed its mode from AP to APMonitor or vice versa.
      	"
	::= {wlsxTrapDefinitionsGroup 1218 }

	wlsxUserEntryAttributesChanged NOTIFICATION-TYPE
		OBJECTS {wlsxTrapTime, wlsxTrapUserIpAddress,wlsxTrapUserPhyAddress,
				wlsxTrapAPBSSID,wlsxTrapAPName,
				wlsxTrapCardSlot,wlsxTrapPortNumber,
				wlsxTrapUserAttributeChangeType,wlsxTrapHTMode,
				wlsxTrapPhyType}
		STATUS		current
		DESCRIPTION
			"			
            This trap indicates that the user entry attributes have changed.
        	"
	::= {wlsxTrapDefinitionsGroup 1219 }

	wlsxPowerSaveDosAttack NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
			This trap indicates that an AP detected a Power Save DoS attack.
			"
	::= {wlsxTrapDefinitionsGroup 1220 }

	wlsxNAPMasterStatusChange NOTIFICATION-TYPE
		OBJECTS {wlsxTrapTime, wlsxTrapAPMacAddress,wlsxTrapApControllerIp,
				wlsxTrapApMasterStatus}
		STATUS		obsolete
		DESCRIPTION
			"			
            This trap indicates that the status of the AP as seen by
            the master controller has changed.
            **NOTE: this notification is obsoleted and replaced by
            wlsxNAPConductorStatusChange
        	"
	::= {wlsxTrapDefinitionsGroup 1221 }

	wlsxNAdhocUsingValidSSID NOTIFICATION-TYPE
		OBJECTS {wlsxTrapTime, wlsxTrapTargetAPBSSID,wlsxTrapTargetAPSSID,
				wlsxTrapSourceMac,wlsxTrapSnr,
				wlsxTrapAPMacAddress,wlsxTrapAPRadioNumber,
				wlsxTrapAPLocation,wlsxTrapAPChannel,
				wlsxTrapAPBand}
		STATUS		current
		DESCRIPTION
			"			
			This trap indicates that an AP detected an ad hoc network node using a valid/protected SSID.
			"
	::= {wlsxTrapDefinitionsGroup 1222 }

	wlsxCRLExpired NOTIFICATION-TYPE
		OBJECTS {wlsxTrapTime, wlsxTrapCaName,wlsxTrapCrlName}
		STATUS		current
		DESCRIPTION
			"			
            This trap indicates that the CRL associated with the particular Trustpoint is expired.
        	"
	::= {wlsxTrapDefinitionsGroup 1223 }

	wlsxMgmtUserAuthenticationFailed NOTIFICATION-TYPE
		OBJECTS {wlsxTrapTime, wlsxTrapUserName,wlsxTrapUserIpAddress,
				wlsxTrapUserPhyAddress,wlsxTrapAuthServerName,
				wlsxTrapAuthServerAddress}
		STATUS		current
		DESCRIPTION
			"			
            This trap indicates that a management user authentication has failed.
        	"
	::= {wlsxTrapDefinitionsGroup 1224 }

	wlsxNConnectionBackfromLocal NOTIFICATION-TYPE
		OBJECTS {wlsxTrapTime, wlsxTrapMasterName,wlsxTrapMasterIp,
				wlsxTrapLocalName,wlsxTrapLocalIp,
				wlsxTrapTimeStr}
		STATUS		obsolete
		DESCRIPTION
			"			
            A trap which indicates that tcp connection between master controller and local controller is back.
        	"
	::= {wlsxTrapDefinitionsGroup 1225 }

	wlsxAPNumUpgradeFailure NOTIFICATION-TYPE
		OBJECTS {wlsxTrapTime, wlsxTrapAPMacAddress,wlsxTrapAPLocation,
				wlsxTrapCount}
		STATUS		current
		DESCRIPTION
			"			
            A trap which indicates the number of upgrade failure of an access point.
        	"
	::= {wlsxTrapDefinitionsGroup 1226 }

	wlsxAPNumWarmStarts NOTIFICATION-TYPE
		OBJECTS {wlsxTrapTime, wlsxTrapAPMacAddress,wlsxTrapAPLocation,
				wlsxTrapAPIpAddress,wlsxTrapCount}
		STATUS		current
		DESCRIPTION
			"			
            A trap which indicates the number of warm starts of an access point.
        	"
	::= {wlsxTrapDefinitionsGroup 1227 }

	wlsxAPNumColdStarts NOTIFICATION-TYPE
		OBJECTS {wlsxTrapTime, wlsxTrapAPMacAddress,wlsxTrapAPLocation,
				wlsxTrapAPIpAddress,wlsxTrapCount}
		STATUS		current
		DESCRIPTION
			"			
            A trap which indicates the number of cold starts of an access point.
        	"
	::= {wlsxTrapDefinitionsGroup 1228 }

	wlsxAPNumDown NOTIFICATION-TYPE
		OBJECTS {wlsxTrapTime, wlsxTrapAPMacAddress,wlsxTrapAPLocation,
				wlsxTrapAPIpAddress,wlsxTrapCount}
		STATUS		current
		DESCRIPTION
			"			
            A trap which indicates the number of down alarms of an access point.
        	"
	::= {wlsxTrapDefinitionsGroup 1229 }

	wlsxAPNumRadioDown NOTIFICATION-TYPE
		OBJECTS {wlsxTrapTime, wlsxTrapAPMacAddress,wlsxTrapAPLocation,
				wlsxTrapAPIpAddress,wlsxTrapCount}
		STATUS		current
		DESCRIPTION
			"			
            A trap which indicates the number of radio down alarms of an access point.
        	"
	::= {wlsxTrapDefinitionsGroup 1230 }

	wlsxNumClockSyncErrors NOTIFICATION-TYPE
		OBJECTS {wlsxTrapTime, wlsxTrapCount}
		STATUS		current
		DESCRIPTION
			"			
            A trap which indicates the total number of clock sync errors between the
            switch and access points.
        	"
	::= {wlsxTrapDefinitionsGroup 1231 }

	wlsxNumColdStart NOTIFICATION-TYPE
		OBJECTS {wlsxTrapTime, wlsxTrapCount}
		STATUS		current
		DESCRIPTION
			"			
            A trap which indicates the number of cold-starts of the switch.
        	"
	::= {wlsxTrapDefinitionsGroup 1232 }

	wlsxNumWarmStart NOTIFICATION-TYPE
		OBJECTS {wlsxTrapTime, wlsxTrapCount}
		STATUS		current
		DESCRIPTION
			"			
            A trap which indicates the number of warm-starts of the switch.
        	"
	::= {wlsxTrapDefinitionsGroup 1233 }

	wlsxWirelessHostedNetworkDetected NOTIFICATION-TYPE
		OBJECTS {wlsxTrapTime, wlsxTrapTargetAPBSSID,wlsxTrapTargetAPSSID,
				wlsxTrapNodeMac,wlsxTrapSnr,
				wlsxTrapClientClassification,wlsxTrapAPMacAddress,
				wlsxTrapAPRadioNumber,wlsxTrapAPLocation,
				wlsxTrapAPChannel,wlsxTrapAPBand}
		STATUS		current
		DESCRIPTION
			"			
            This trap indicates that an AP detected a wireless client that is
            hosting a softAP. The softAP could be used to share the hosting 
            client's  wired or wireless network connection with other wireless users. 
        	"
	::= {wlsxTrapDefinitionsGroup 1234 }

	wlsxClientAssociatedToHostedNetwork NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
            This trap indicates that an AP detected that a wireless client associated 
            to an access point that is hosted by another wireless client.
        	"
	::= {wlsxTrapDefinitionsGroup 1235 }

	wlsxThresholdExceeded NOTIFICATION-TYPE
		OBJECTS {wlsxTrapTime, wlsxThresholdResourceType,wlsxThresholdResourceName,
				wlsxThresholdValue,wlsxResourceValue}
		STATUS		current
		DESCRIPTION
			"			
            A trap indicates a particular resource under monitoring has gone above the threshold specified.
        	"
	::= {wlsxTrapDefinitionsGroup 1236 }

	wlsxThresholdCleared NOTIFICATION-TYPE
		OBJECTS {wlsxTrapTime, wlsxThresholdResourceType,wlsxThresholdResourceName,
				wlsxThresholdValue,wlsxResourceValue}
		STATUS		current
		DESCRIPTION
			"			
            A trap indicates a particular resource under monitoring has come below the threshold specified.
        	"
	::= {wlsxTrapDefinitionsGroup 1237 }

	wlsxWirelessHostedNetworkContainment NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
            This trap indicates that containment is being enforced on a client associated to a hosted network.
        	"
	::= {wlsxTrapDefinitionsGroup 1238 }

	wlsxHostOfWirelessNetworkContainment NOTIFICATION-TYPE
		OBJECTS {wlsxTrapTime, wlsxTrapTargetAPBSSID,wlsxTrapTargetAPSSID,
				wlsxTrapNodeMac,wlsxTrapSnr,
				wlsxTrapAPBSSID,wlsxTrapAPMacAddress,
				wlsxTrapAPRadioNumber,wlsxTrapAPLocation,
				wlsxTrapAPChannel,wlsxTrapAPBand}
		STATUS		current
		DESCRIPTION
			"			
            This trap indicates that containment is being enforced on a client that is hosting a wireless hosted network.
        	"
	::= {wlsxTrapDefinitionsGroup 1239 }

	wlsxEnhancedAdhocContainment NOTIFICATION-TYPE
		OBJECTS {wlsxTrapTime, wlsxTrapTargetAPBSSID,wlsxTrapTargetAPSSID,
				wlsxTrapNodeMac,wlsxTrapAPMacAddress,
				wlsxTrapAPRadioNumber,wlsxTrapAPLocation,
				wlsxTrapAPChannel,wlsxTrapAPBand}
		STATUS		current
		DESCRIPTION
			"			
            This trap indicates that an AP has attempted to contain an adhoc node by disconnecting it from other members of the adhoc network.
        	"
	::= {wlsxTrapDefinitionsGroup 1240 }

	wlsxPowerSupplyOKTrap NOTIFICATION-TYPE
		OBJECTS {wlsxTrapTime, wlsxTrapPowerSupplyNumber}
		STATUS		current
		DESCRIPTION
			"			
             This trap indicates that the system power supply condition have
             returned to normal operation status.
         	"
	::= {wlsxTrapDefinitionsGroup 1241 }

	wlsxPowerSupplyFailureTrap NOTIFICATION-TYPE
		OBJECTS {wlsxTrapTime, wlsxTrapPowerSupplyNumber}
		STATUS		current
		DESCRIPTION
			"			
             A trap which indicates that the power supply has failed.
         	"
	::= {wlsxTrapDefinitionsGroup 1242 }

	wlsxFanTrayRemovedTrap NOTIFICATION-TYPE
		OBJECTS {wlsxTrapTime, wlsxTrapFanTrayNumber}
		STATUS		current
		DESCRIPTION
			"			
             A Trap which indicates that a fan tray is removed.
         	"
	::= {wlsxTrapDefinitionsGroup 1243 }

	wlsxFanTrayInsertedTrap NOTIFICATION-TYPE
		OBJECTS {wlsxTrapTime, wlsxTrapFanTrayNumber}
		STATUS		current
		DESCRIPTION
			"			
             A Trap which indicates that a fan tray is inserted.
         	"
	::= {wlsxTrapDefinitionsGroup 1244 }

	wlsxPowerSupplyMissingTrap NOTIFICATION-TYPE
		OBJECTS {wlsxTrapTime, wlsxTrapPowerSupplyNumber}
		STATUS		current
		DESCRIPTION
			"			
             A Trap which indicates that the power supply is missing.
         	"
	::= {wlsxTrapDefinitionsGroup 1245 }

	wlsxStackTopologyChangeTrap NOTIFICATION-TYPE
		OBJECTS {wlsxTrapTime, wlsxStackMemberMacAddress,wlsxStackPrevSlot,
				wlsxStackCurrentSlot,wlsxStackPrevState,
				wlsxStackCurrentState,wlsxStackChangeEvent}
		STATUS		current
		DESCRIPTION
			"			
              When change happens in any topology of the stack element in the
              stack, then a notification is sent to the Management Entity.
          	"
	::= {wlsxTrapDefinitionsGroup 1246 }

	wlsxStackIfStateChangeTrap NOTIFICATION-TYPE
		OBJECTS {wlsxTrapTime, wlsxStackMemberMacAddress,wlsxStackMemberSlotNumber,
				wlsxStackIfName,wlsxStackProtoIfTopoJoined}
		STATUS		current
		DESCRIPTION
			"			
              When any stacking interface in any stack element joins or leaves
              stacking topology, then a notification is sent to the Management
              Entity with slot and interface information.
          	"
	::= {wlsxTrapDefinitionsGroup 1247 }

	wlsxLicenseServerExpiry NOTIFICATION-TYPE
		OBJECTS {wlsxTrapTime, wlsxTrapLicenseServerDaysRemaining}
		STATUS		current
		DESCRIPTION
			"			
            A Trap which indicates that licenses sent from the license 
            server will expire in wlsxTrapLicenseServerDaysRemaining days.
        	"
	::= {wlsxTrapDefinitionsGroup 1248 }

	wlsxLicenseClientExpiry NOTIFICATION-TYPE
		OBJECTS {wlsxTrapTime, wlsxTrapLicenseClientDaysRemaining}
		STATUS		current
		DESCRIPTION
			"			
            A Trap which indicates that licenses contributed by a license 
            client will expire in wlsxTrapLicenseClientDaysRemaining days.
        	"
	::= {wlsxTrapDefinitionsGroup 1249 }

	wlsxIfStateChangeTrap NOTIFICATION-TYPE
		OBJECTS {wlsxTrapTime, wlsxIfIndex,wlsxIfState,
				wlsxIfStateChangeReason}
		STATUS		current
		DESCRIPTION
			"			
              When the link state of an interface changes due to reason
              specified by wlsxIfStateChangeReason object, a notification is
              sent to the Management Entity with reason for this state change
              and interface information.
          	"
	::= {wlsxTrapDefinitionsGroup 1250 }

	wlsxWMSOffloadRecommended NOTIFICATION-TYPE
		OBJECTS {wlsxTrapTime}
		STATUS		current
		DESCRIPTION
			"			
              This trap indicates that current state in the WMS module shows that WMS is reaching capacity, and 
              so it is recommended to enable WMS-Offload.  
          	"
	::= {wlsxTrapDefinitionsGroup 1251 }

	wlsxAPActiveUplinkChanged NOTIFICATION-TYPE
		OBJECTS {wlsxTrapTime, wlsxTrapAPMacAddress,wlsxTrapAPPreviousUplinkType,
				wlsxTrapAPPreviousUplinkActiveTime,wlsxTrapAPActiveUplinkType,
				wlsxTrapAPUplinkChangeReason}
		STATUS		current
		DESCRIPTION
			"			
              When the active uplink of an AP changes, a notification is
              sent to the Management Entity with the new uplink type
          	"
	::= {wlsxTrapDefinitionsGroup 1252 }

	wlsxCertExpiringSoon NOTIFICATION-TYPE
		OBJECTS {wlsxTrapTime, wlsxTrapExpiringCertName}
		STATUS		current
		DESCRIPTION
			"			
              This trap indicates that a particular Certificate is going to expire in less than 60 days.
          	"
	::= {wlsxTrapDefinitionsGroup 1253 }

	wlsxCertExpired NOTIFICATION-TYPE
		OBJECTS {wlsxTrapTime, wlsxTrapExpiredCertName}
		STATUS		current
		DESCRIPTION
			"			
              This trap indicates that a particular Certificate has expired and is no longer valid.
          	"
	::= {wlsxTrapDefinitionsGroup 1254 }

	wlsxAPManagedModeConfigFailureTrap NOTIFICATION-TYPE
		OBJECTS {wlsxTrapTime, wlsxTrapAPMacAddress,wlsxTrapAPManagedModeConfigFailure}
		STATUS		current
		DESCRIPTION
			"			
            This trap indicates that config apply has failed on the IAP.
          	"
	::= {wlsxTrapDefinitionsGroup 1255 }

	wlsxNAuthServerAcctTimedOut NOTIFICATION-TYPE
		OBJECTS {wlsxTrapTime, wlsxTrapUserName,wlsxTrapUserIpAddress,
				wlsxTrapUserPhyAddress,wlsxTrapAuthServerName,
				wlsxTrapAuthServerAddress,wlsxTrapAPBSSID,
				wlsxTrapAPName}
		STATUS		current
		DESCRIPTION
			"			
         This trap indicates that the authentication server accounting timed out.
        	"
	::= {wlsxTrapDefinitionsGroup 1256 }

	wlsxAPUp NOTIFICATION-TYPE
		OBJECTS {wlsxTrapTime, wlsxTrapAPMacAddress,wlsxTrapAPName,
				wlsxTrapAPIpAddress}
		STATUS		current
		DESCRIPTION
			"			
            A Trap which indicates that AP is Up with AP name and IP address.
        	"
	::= {wlsxTrapDefinitionsGroup 1257 }

	wlsxAPDown NOTIFICATION-TYPE
		OBJECTS {wlsxTrapTime, wlsxTrapAPMacAddress,wlsxTrapAPName,
				wlsxTrapAPIpAddress}
		STATUS		current
		DESCRIPTION
			"			
            A Trap which indicates that AP is Down with AP name and IP address.
        	"
	::= {wlsxTrapDefinitionsGroup 1258 }

	wlsxPortalServerDown NOTIFICATION-TYPE
		OBJECTS {wlsxTrapTime, wlsxTrapPortalServerName,wlsxTrapPortalServerAddress,
				wlsxTrapAPName,wlsxTrapPortalServerDownReason}
		STATUS		current
		DESCRIPTION
			"			
         This trap indicates that the captive portal server is down.
        	"
	::= {wlsxTrapDefinitionsGroup 1259 }

	wlsxPortalServerUp NOTIFICATION-TYPE
		OBJECTS {wlsxTrapTime, wlsxTrapPortalServerName,wlsxTrapPortalServerAddress,
				wlsxTrapAPName}
		STATUS		current
		DESCRIPTION
			"			
         This trap indicates that the captive portal server is up.
        	"
	::= {wlsxTrapDefinitionsGroup 1260 }

	wlsxNAdhocUsingValidSSIDContainment NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
            This trap indicates that containment is being enforced on an ad hoc wireless network node using a valid/protected SSID.
        	"
	::= {wlsxTrapDefinitionsGroup 1261 }

	wlsxLicensePlatformMismatch NOTIFICATION-TYPE
		OBJECTS {wlsxTrapTime, wlsxTrapLicensePlatformMismatchKey}
		STATUS		current
		DESCRIPTION
			"			
            A Trap which indicates that license to be installed is not compatible with the platform.
        	"
	::= {wlsxTrapDefinitionsGroup 1262 }

	wlsxIAPVoiceClientLocationUpdate NOTIFICATION-TYPE
		OBJECTS {wlsxTrapTime, wlsxTrapVcIpAddress,wlsxTrapVcMacAddress,
				wlsxTrapAPMacAddress,wlsxTrapAPName}
		STATUS		current
		DESCRIPTION
			"			
           The trap represents a IAP voice client location update.
        	"
	::= {wlsxTrapDefinitionsGroup 1263 }

	wlsxNAceUsageThreshold NOTIFICATION-TYPE
		OBJECTS {wlsxTrapTime}
		STATUS		current
		DESCRIPTION
			"			
            A trap which indicates that the ACE Entries table has reached
            eighty percent of the maximum limit.
        	"
	::= {wlsxTrapDefinitionsGroup 1264 }

	wlsxNWebCCLicenseEnforcement NOTIFICATION-TYPE
		OBJECTS {wlsxTrapTime}
		STATUS		current
		DESCRIPTION
			"			
            A Trap which indicates that web-cc license enforcement has been triggered.
        	"
	::= {wlsxTrapDefinitionsGroup 1265 }

	wlsxNFanAbsent NOTIFICATION-TYPE
		OBJECTS {wlsxTrapTime, wlsxTrapFanNumber}
		STATUS		current
		DESCRIPTION
			"			
            A trap which indicates that the fan is absent.
        	"
	::= {wlsxTrapDefinitionsGroup 1266 }

	wlsxWPAFTAttack NOTIFICATION-TYPE
		OBJECTS {wlsxTrapTime, wlsxTrapAPMacAddress,wlsxTrapAPRadioNumber,
				wlsxTrapAPLocation,wlsxTrapNodeMac,
				wlsxTrapAPChannel,wlsxTrapTargetAPBSSID,
				wlsxTrapAPBand}
		STATUS		current
		DESCRIPTION
			"			
            This trap indicates there is a possible attack of the Fast BSS Transition causing a WPA key re-installation.
            This can be indicative of a security breach where an attacker can hijack a client's association and/or
            decrypt an otherwise secure connection.
        	"
	::= {wlsxTrapDefinitionsGroup 1267 }

	wlsxMitMDetected NOTIFICATION-TYPE
		OBJECTS {wlsxTrapTime, wlsxTrapAPLocation,wlsxTrapAPMacAddress,
				wlsxTrapAPRadioNumber,wlsxTrapSourceMac,
				wlsxTrapTargetAPBSSID,wlsxTrapAPChannel,
				wlsxTrapSnr,wlsxTrapAPBand}
		STATUS		current
		DESCRIPTION
			"			
            This trap indicates that an AP detected a possible channel-based Man in the Middle attack by someone using spoofed beacons with an invalid Channel Switch Announcement.
        	"
	::= {wlsxTrapDefinitionsGroup 1268 }

	wlsxAPPortUp NOTIFICATION-TYPE
		OBJECTS {wlsxTrapTime, wlsxTrapAPMacAddress,wlsxTrapAPName,
				wlsxTrapPortNumber,wlsxTrapOperStatus}
		STATUS		current
		DESCRIPTION
			"			
            This trap indicates that AP's secure jack port is Up.
        	"
	::= {wlsxTrapDefinitionsGroup 1269 }

	wlsxAPPortDown NOTIFICATION-TYPE
		OBJECTS {wlsxTrapTime, wlsxTrapAPMacAddress,wlsxTrapAPName,
				wlsxTrapPortNumber,wlsxTrapOperStatus}
		STATUS		current
		DESCRIPTION
			"			
            This trap indicates that AP's secure jack port is Down.
        	"
	::= {wlsxTrapDefinitionsGroup 1270 }

	wlsxAPLoopDetected NOTIFICATION-TYPE
		OBJECTS {wlsxTrapTime, wlsxTrapAPMacAddress,wlsxTrapAPName,
				wlsxTrapPortNumber}
		STATUS		current
		DESCRIPTION
			"			
            This trap indicates that loop is detected on AP's secure jack port.
        	"
	::= {wlsxTrapDefinitionsGroup 1271 }

	wlsxAPBROADCASTSTORM NOTIFICATION-TYPE
		OBJECTS {wlsxTrapTime, wlsxTrapAPMacAddress,wlsxTrapAPName,
				wlsxTrapPortNumber}
		STATUS		current
		DESCRIPTION
			"			
            This trap indicates that broadcast storm is detected on AP's secure jack port.
        	"
	::= {wlsxTrapDefinitionsGroup 1272 }

	wlsxAPIPConflict NOTIFICATION-TYPE
		OBJECTS {wlsxTrapTime, wlsxTrapAPMacAddress,wlsxTrapAPName,
				wlsxTrapAPIpAddress,wlsxTrapSourceMac,
				wlsxTrapCount}
		STATUS		current
		DESCRIPTION
			"			
            This trap indicates that an IP conflict is detected on AP.
        	"
	::= {wlsxTrapDefinitionsGroup 1273 }

	wlsxCLEARPASSSERVERINVALID NOTIFICATION-TYPE
		OBJECTS {wlsxTrapTime, wlsxTrapAuthServerName}
		STATUS		current
		DESCRIPTION
			"			
            This trap indicates that CLEARPASS server is not valid when using the CA to verity the server for download-role.
        	"
	::= {wlsxTrapDefinitionsGroup 1274 }

	wlsxNLowOnFlash1Space NOTIFICATION-TYPE
		OBJECTS {wlsxTrapTime}
		STATUS		current
		DESCRIPTION
			"			
            A Trap which indicates that the controller is running low on flash1 space.
        	"
	::= {wlsxTrapDefinitionsGroup 1275 }

	wlsxFlash1SpaceOK NOTIFICATION-TYPE
		OBJECTS {wlsxTrapTime}
		STATUS		current
		DESCRIPTION
			"			
            This trap which indicates that the system flash1 space is back
            to a sufficient level.
        	"
	::= {wlsxTrapDefinitionsGroup 1276 }

	wlsxTHERMALSHUTDOWN NOTIFICATION-TYPE
		OBJECTS {wlsxTrapTime, wlsxTrapAPMacAddress,wlsxTrapAPName,
				wlsxTrapAPIpAddress}
		STATUS		current
		DESCRIPTION
			"			
            This trap indicates that an AP is overheat and in shutdown mode.
        	"
	::= {wlsxTrapDefinitionsGroup 1277 }

	wlsxPhonyBSSIDDetected NOTIFICATION-TYPE
		OBJECTS {wlsxTrapTime, wlsxTrapAPLocation,wlsxTrapAPMacAddress,
				wlsxTrapAPRadioNumber,wlsxTrapTargetAPBSSID,
				wlsxTrapAPChannel,wlsxTrapTargetAPName,
				wlsxTrapTargetAPMac,wlsxTrapAPBand}
		STATUS		current
		DESCRIPTION
			"			
             This trap indicates that an AP detected a non-configured BSSID that should belong to one of our known valid APs.
         	"
	::= {wlsxTrapDefinitionsGroup 1278 }

	wlsxAPUSBPLUGALARM NOTIFICATION-TYPE
		OBJECTS {wlsxTrapTime, wlsxTrapAPMacAddress,wlsxTrapAPName,
				wlsxTrapUSBVendorProductID,wlsxTrapUSBVendorProductID,
				wlsxTrapAPUSBStatus}
		STATUS		current
		DESCRIPTION
			"			
            This trap indicates that an USB device is plugged in or out to an AP.
        	"
	::= {wlsxTrapDefinitionsGroup 1279 }

	wlsxNSwitchIPv6Changed NOTIFICATION-TYPE
		OBJECTS {wlsxTrapTime, wlsxTrapSwitchIpv6}
		STATUS		current
		DESCRIPTION
			"			
            This trap indicates that the controller IPv6 address has changed.
        	"
	::= {wlsxTrapDefinitionsGroup 1280 }

	wlsxNDot1xThresholdLimitHit NOTIFICATION-TYPE
		OBJECTS {wlsxTrapTime}
		STATUS		current
		DESCRIPTION
			"			
             A Trap which indicates that the controller is running on high optimum limit.
         	"
	::= {wlsxTrapDefinitionsGroup 1281 }

	wlsxNDot1xTotalLimitHit NOTIFICATION-TYPE
		OBJECTS {wlsxTrapTime}
		STATUS		current
		DESCRIPTION
			"			
             A Trap which indicates that the controller is running on full optimum limit.
         	"
	::= {wlsxTrapDefinitionsGroup 1282 }

	wlsxClusterVlanProbeStatus NOTIFICATION-TYPE
		OBJECTS {wlsxTrapTime, wlsxTrapPeerIpAddress,wlsxTrapConnectionStatus,
				wlsxTrapFailedVlan}
		STATUS		current
		DESCRIPTION
			"			
              This trap indicates the cluster VLAN probe status.
          	"
	::= {wlsxTrapDefinitionsGroup 1283 }

	wlsxClientRejectedByMaxClientCount NOTIFICATION-TYPE
		OBJECTS {wlsxTrapTime, wlsxTrapUserPhyAddress,wlsxTrapAPBSSID,
				wlsxTrapAPMacAddress,wlsxTrapAPName,
				wlsxTrapEssid}
		STATUS		current
		DESCRIPTION
			"			 
              This trap indicates the client is rejected by the max client count.
          	"
	::= {wlsxTrapDefinitionsGroup 1284 }

	wlsxClientPskAuthenticationFailed NOTIFICATION-TYPE
		OBJECTS {wlsxTrapTime, wlsxTrapUserPhyAddress,wlsxTrapAuthFailureReason,
				wlsxTrapAPBSSID,wlsxTrapAPMacAddress,
				wlsxTrapAPName,wlsxTrapEssid}
		STATUS		current
		DESCRIPTION
			"			 
              This trap indicates the client PSK Authentication Failed. 
          	"
	::= {wlsxTrapDefinitionsGroup 1285 }

	wlsxNStationAddedToDenyList NOTIFICATION-TYPE
		OBJECTS {wlsxTrapTime, wlsxTrapNodeMac,wlsxTrapStationDenyListReason,
				wlsxTrapStationDenyListReasonStr}
		STATUS		current
		DESCRIPTION
			"			
            This trap indicates that the station is added to denylist.
        	"
	::= {wlsxTrapDefinitionsGroup 1286 }

	wlsxNStationRemovedFromDenyList NOTIFICATION-TYPE
		OBJECTS {wlsxTrapTime, wlsxTrapNodeMac}
		STATUS		current
		DESCRIPTION
			"			
            This trap indicates that the station is removed from denylist.
        	"
	::= {wlsxTrapDefinitionsGroup 1287 }

	wlsxNAPConductorStatusChange NOTIFICATION-TYPE
		OBJECTS {wlsxTrapTime, wlsxTrapAPMacAddress,wlsxTrapApControllerIp,
				wlsxTrapApConductorStatus}
		STATUS		current
		DESCRIPTION
			"			
            This trap indicates that the status of the AP as seen by
            the conductor controller has changed.
        	"
	::= {wlsxTrapDefinitionsGroup 1288 }

	wlsxGhostTunnelserverAttack NOTIFICATION-TYPE
		OBJECTS {wlsxTrapTime, wlsxTrapAPMacAddress,wlsxTrapAPRadioNumber,
				wlsxTrapAPLocation}
		STATUS		current
		DESCRIPTION
			"			
            This trap indicates there is a possible attack of the Ghost Tunnel.
            This can be airgap atttack only by beacon and probe request where an attacker can hijack a client.
        	"
	::= {wlsxTrapDefinitionsGroup 1289 }

	wlsxGhostTunnelclientAttack NOTIFICATION-TYPE
		OBJECTS {wlsxTrapTime, wlsxTrapAPMacAddress,wlsxTrapAPRadioNumber,
				wlsxTrapAPLocation}
		STATUS		current
		DESCRIPTION
			"			
            This trap indicates there is a possible attack of the Ghost Tunnel.
            This can be airgap atttack only by beacon and probe request where an attacker can hijack a client.
        	"
	::= {wlsxTrapDefinitionsGroup 1290 }

	wlsxPeerAssociatedToWifiDirectGo NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
             This trap indicates that an AP detected a wireless client associated to a WIFI-Direct Group Owner.
         	"
	::= {wlsxTrapDefinitionsGroup 1291 }

	wlsxPeerAssociatedToWifiDirectGoContainment NOTIFICATION-TYPE
		OBJECTS {wlsxTrapTime, wlsxTrapTargetAPBSSID,wlsxTrapTargetAPSSID,
				wlsxTrapNodeMac,wlsxTrapSnr,
				wlsxTrapAPMacAddress,wlsxTrapAPRadioNumber,
				wlsxTrapAPLocation,wlsxTrapAPChannel,
				wlsxTrapAPBand}
		STATUS		current
		DESCRIPTION
			"			
             This trap indicates that containment is being enforced on a wireless client that is associated to a WIFI-Direct Group Owner.
         	"
	::= {wlsxTrapDefinitionsGroup 1292 }

	wlsxLicenseThresholdLimitHit NOTIFICATION-TYPE
		OBJECTS {wlsxTrapTime, wlsxLicensePoolName,wlsxLicenseType}
		STATUS		current
		DESCRIPTION
			"			
             A Trap which indicates that the Licenses are running on high optimum limit.
         	"
	::= {wlsxTrapDefinitionsGroup 1293 }

END
