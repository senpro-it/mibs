-- ZyXEL Communications Corporation
-- Private Enterprise MIB definition 
  
-- This file describes the ZyXEL Communications Corporation Enterprise MIB.
-- It contains ZyXEL products OIDs, and common managed objects.

-- ZYXEL-SUBNET-BASED-VLAN-MIB.mib
-- Revision 1.5  2013/12/06 

ZYXEL-SUBNET-BASED-VLAN-MIB DEFINITIONS ::= BEGIN

    IMPORTS
	OBJECT-TYPE
		FROM SNMPv2-SMI			-- RFC2578	
		
	MODULE-IDENTITY
		FROM SNMPv2-SMI
	
	RowStatus
		FROM SNMPv2-TC			-- RFC2579
		
	DisplayString                                          
	  	FROM SNMPv2-TC
	  	
	EnabledStatus
		FROM  P-BRIDGE-MIB
	
    IpAddress
        FROM SNMPv2-SMI

	esMgmt			
		FROM ZYXEL-ES-SMI;

	zyxelSubnetBasedVlan MODULE-IDENTITY
		LAST-UPDATED	"201207010000Z"    
		ORGANIZATION "Enterprise Solution ZyXEL"     
		CONTACT-INFO
			""	   
		DESCRIPTION
			"The subtree for subnet-based VLAN"
		::= { esMgmt 80 }	
		
	zyxelSubnetBasedVlanSetup 	OBJECT IDENTIFIER ::= { zyxelSubnetBasedVlan 1 }
		

-- *******************************************************************
-- *
-- * zyxelSubnetBasedVlanSetup
-- *
-- *******************************************************************

-- zyxelSubnetBasedVlanState
        zySubnetBasedVlanState OBJECT-TYPE
        SYNTAX  EnabledStatus
        MAX-ACCESS  read-write
        STATUS  current
        DESCRIPTION
        	"Enable/Disable subnet-based VLAN feature on the switch."
        ::= { zyxelSubnetBasedVlanSetup 1 }

-- zyxelSubnetBasedVlanDhcpVlanOverrideState
        zySubnetBasedVlanDhcpVlanOverrideState OBJECT-TYPE
        SYNTAX  EnabledStatus
        MAX-ACCESS  read-write
        STATUS  current
        DESCRIPTION
        	" Enable/Disable DHCP VLAN override to force the DHCP clients in this IP subnet 
        		to obtain their IP address through the DHCP VLAN."
        ::= { zyxelSubnetBasedVlanSetup 2 }
             
-- zyxelSubnetBasedVlanMaxNumberOfVlans    
        zySubnetBasedVlanMaxNumberOfVlans OBJECT-TYPE
        SYNTAX  INTEGER
        MAX-ACCESS  read-only
        STATUS  current
        DESCRIPTION
        	" The maximum number of subnet bsed VLAN that can be created"
        ::= { zyxelSubnetBasedVlanSetup 3 }
 
-- zyxelSubnetBasedVlanTable
	    zyxelSubnetBasedVlanTable  OBJECT-TYPE
	    SYNTAX	SEQUENCE OF ZyxelSubnetBasedVlanEntry 
	    MAX-ACCESS  not-accessible
	    STATUS  current
	    DESCRIPTION
	             	"The table cantains subnet based VLAN configuration."
	    ::= { zyxelSubnetBasedVlanSetup 4 }	

		zyxelSubnetBasedVlanEntry  OBJECT-TYPE
        SYNTAX	ZyxelSubnetBasedVlanEntry 
        MAX-ACCESS	not-accessible
        STATUS	current
        DESCRIPTION    	"An entry cantains subnet based VLAN configuration."
        INDEX          	{zySubnetBasedVlanSourceIpAddress , zySubnetBasedVlanSourceMaskBits}
        ::= { zyxelSubnetBasedVlanTable 1 }

        ZyxelSubnetBasedVlanEntry ::=
           SEQUENCE {
            zySubnetBasedVlanSourceIpAddress	IpAddress,
            zySubnetBasedVlanSourceMaskBits		INTEGER,
            zySubnetBasedVlanName				DisplayString,     
            zySubnetBasedVlanVid				INTEGER,
            zySubnetBasedVlanPriority			INTEGER,          
            zySubnetBasedVlanRowStatus			RowStatus            
           }

        zySubnetBasedVlanSourceIpAddress OBJECT-TYPE
        SYNTAX  IpAddress
        MAX-ACCESS  not-accessible
        STATUS  current
        DESCRIPTION
                      	"Enter the source ip adress of the subnet for which you want to configure this subnet based VLAN"
        ::= { zyxelSubnetBasedVlanEntry 1 }


        zySubnetBasedVlanSourceMaskBits OBJECT-TYPE
        SYNTAX  INTEGER (1..32)
        MAX-ACCESS  not-accessible
        STATUS  current
        DESCRIPTION
                      	"Enter the bit number of the subnet mask.  To find the bit number, 
                      	convert the subnet mask to binary format and add all the 1's in binary."
        ::= { zyxelSubnetBasedVlanEntry 2 }
             
        zySubnetBasedVlanName OBJECT-TYPE
        SYNTAX  DisplayString (SIZE (0..32))
        MAX-ACCESS  read-write
        STATUS  current
        DESCRIPTION
                      	"Name to identify this subnet based VLAN."
        ::= { zyxelSubnetBasedVlanEntry 3 }
                                                   
        zySubnetBasedVlanVid OBJECT-TYPE
        SYNTAX  INTEGER (1..4094)
        MAX-ACCESS  read-write
        STATUS  current
        DESCRIPTION
                      	"ID of a VLAN with which the untagged frames from the IP subnet specified in this subnet based VLAN are tagged. 
                      	This must be an existing VLAN which you defined."
        ::= { zyxelSubnetBasedVlanEntry 4 }


        zySubnetBasedVlanPriority OBJECT-TYPE
        SYNTAX  INTEGER (0..7)
        MAX-ACCESS  read-write
        STATUS  current
        DESCRIPTION
                      	"Priority level that the switch assigns to frames belonging to this VLAN."
        ::= { zyxelSubnetBasedVlanEntry 5 }

        zySubnetBasedVlanRowStatus OBJECT-TYPE
        SYNTAX  RowStatus
        MAX-ACCESS  read-create
        STATUS  current
        DESCRIPTION
                      	"This object allows entries to be created and deleted from the subnet based VLAN table."
        ::= { zyxelSubnetBasedVlanEntry 6 } 

  END
